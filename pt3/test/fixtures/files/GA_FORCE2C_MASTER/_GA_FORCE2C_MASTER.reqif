# IBM Rational DOORS, 27 January 2021

# Specification: 854-100994-HRD-001
- ReqIF.Description: Requirements for SBC314C CBA
- ReqIF.Name: 854-100994-HRD-001

## 914: Overview
- Category: Heading

### 915
The main features of the SBC314C are:
- One PowerPC processor option
- NXP T2081 – Four 64-bit dual-threaded cores with Altivec at up to 1.8GHz
- 8GBytes DDR3L SDRAM
- 256MByte NOR FLASH
- 64Gbyte SATA Solid State Drive
- One XMC Site
- Ethernet/Serial/USB/SATA Interfaces
- 8 lanes Gen2-capable PCI Express to VPX connector
- 8 General Purpose IO Pins (GPIO)
- SPI NVRAM
- Category: Information

### 916
The architecture of the SBC314C shall be as shown below
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- Category: Requirement
- Derived: False
- Safety: False
- Verification Details: Inspection of the schematic and BOM.
  Analysis of component datasheets.
- Verification Method: Inspection, Analysis

### 2105: Applicable Documents
- Category: Heading

#### 2106
FORCE2C-0HG-9001 FORCE2C Internal Interface Control Document
854-100994-HRD-000 FORCE2C Specification
- Category: Information

## 430: SBC314C Functional Specification
- Category: Heading

### 431: Integrated Host Processor
- Category: Heading

#### 632
The SBC314C shall support a single processor site.
- Category: Requirement
- Derived: True
- Derived Req Justification: Design decision based on FORCE2 system specifications.
- Safety: False
- Verification Details: [R] Review design - one processor site
- Verification Method: Inspection

#### 633
The SBC314C shall support the NXP QorIQ T2081 integrated host processor.
- Category: Requirement
- Derived: False
- Safety: False
- Verification Details: [I] Inspect UUT and BOM for specified processor
  [DT] All Proving tests carried out on T2081 variant
  [T] All Production tests carried out on T2081 variant
- Verification Method: Inspection, Design Proving Test, Production Test

#### 660: Operating Frequency
- Category: Heading

##### 1120
The SBC314C shall support the T2081 processor operating at a core frequency of 1800MHz.
- Category: Requirement
- Derived: False
- Safety: False
- Verification Details: Analysis of processor datasheet.
- Verification Method: Analysis

#### 790: Essential CPU Features
- Category: Heading

##### 821
This section lists features provided by the integrated host processor, which are shown to demonstrate that low-level features that may be required by a customer are present within the design. They do not form requirements of the board itself as they are provided by virtue of the processor being present.
For more details on these features, consult the NXP Reference Manual for the relevant processor device or core.
- Category: Information

##### 867: Caches
- Category: Heading

###### 868
The e6500 core in the T-series integrated host processor contains a 32KB L1 instruction cache and 32KB L1 data cache.
- Category: Information

###### 869
The L1 caches incorporate data and tag parity protection
- Category: Information

###### 870
The T-series integrated host processors contain 2MB shared L2 caches
- Category: Information

###### 871
The L2 caches incorporate ECC protection (data, tag and status)
- Category: Information

##### 865: Memory Management Unit
- Category: Heading

###### 866
The e6500 core in the T-series integrated host processor contains a sophisticated Memory Management Unit (MMU) providing highly configurable memory protection features.
- Category: Information

##### 791: Timers
- Category: Heading

###### 792
The T-series integrated host processors contain one 32-bit Decrementer timer per thread, i.e. 8 for the T2081.
- Category: Information

###### 794
The T-series integrated host processors contain one 64-bit Timebase counter timer per physical core, i.e. 4 for the T2081.
- Category: Information

###### 822
The T-series integrated host processors contain eight 31-bit global timers within the Multicore Programmable Interrupt Controller (MPIC) block.
- Category: Information

###### 824
Up to 4 MPIC global timers can be cascaded to form larger timers.
- Category: Information

###### 825
All of these timers are provided by hardware; but, some may be utilized by the operating system and therefore not available to the user.
- Category: Information

##### 1169: UARTs
- Category: Heading

###### 1170
The T-series integrated host processors contain two UARTs.
- Category: Information

###### 805
The UARTs incorporate FIFO data buffering (transmit and receive) in order to minimise processor overhead
- Category: Information

##### 795: DMA Controllers
- Category: Heading

###### 796
The T2081 processor contains three 8-channel DMA controllers.
- Category: Information

#### 951: CPU Configuration
- Category: Heading

##### 952: Strapping Options
- Category: Heading

###### 953
The CPU strapping options are set by the FPGA. See the FPGA specification for details
- Category: Information

##### 954: Reset Configuration Word
- Category: Heading

###### 955
The RCW is provided by the FPGA device. See the FPGA section and detailed specification for further details
- Category: Information

##### 2149: Security Fuse
- Category: Heading

###### 2150
There SHALL be a switch to gate 1.8V (P1V8) to the security fuse power supply (PROG_SFP) input pin (F12) of the T2081 processor.
- Category: Requirement
- Derived: True
- Derived Req Justification: This hardware exist on the SBC314C board for possible to allow its possible future use in products that allow user programming of the T2081 security fuse.
- Safety: False

###### 2151
The T2081 security fuse power supply gate SHALL be deactivated.
- Category: Requirement
- Derived: True
- Derived Req Justification: It as been decided that the T2081 security fuse will not be user programmable on the FORCE2C.
- Safety: False

### 438: Memory
- Category: Heading

#### 439: Main Memory
- Category: Heading

##### 663: Layout
- Category: Heading

###### 440
The SBC314C shall provide one bank of nine DDR3L SDRAM devices connected to the memory controller within the processor.
- Category: Requirement
- Derived: False
- Safety: False
- Verification Details: [I] Inspect circuit diagram for memory channel arrangement
  [DT] Proving tests using FTS software or equivalent method
  [T] Production tests using FTS software
- Verification Method: Inspection, Design Proving Test, Production Test

###### 441
The main memory shall incorporate ECC protection
- Category: Requirement
- Derived: False
- Safety: True
- Verification Details: [DT] ECC Proving test using FTS software or equivalent
  [T] Production tests using FTS software
- Verification Method: Design Proving Test, Production Test

###### 729
The main memory ECC shall be capable of detecting single and two bit errors
- Category: Requirement
- Derived: False
- Safety: True
- Verification Details: Analysis of memory sheets.
- Verification Method: Analysis

###### 730
The main memory ECC shall be capable of correcting single bit errors
- Category: Requirement
- Derived: False
- Safety: True
- Verification Details: Analysis of memory sheets.
- Verification Method: Analysis

###### 893
The T-series integrated host processor on-chip memory controllers contain built-in-test features in order to verify the correct operation of the ECC protection
- Category: Information

##### 665: Capacity
- Category: Heading

###### 442
The main memory shall support 8Gbit monolithic devices to give a 8GByte total size
- Category: Requirement
- Derived: False
- Safety: False
- Verification Details: [I] Inspect BOM for 4Gbit monolithic RAMs
  [T] 4GB RAM verified on every board
- Verification Method: Inspection, Production Test

###### 959
The supported RAM configurations using the combined footprint are shown below:
- Category: Information

###### 1439
| Total RAM | No. of Devices | Device Type | No. of Ranks per Controller |
| --- | --- | --- | --- |
| 8 GBytes | 9 | 8Gbit monolithic | 1 |
| 8 GBytes | 9 | 8Gbit twin-die | 2 |
|  | 9 | 8Gbit monolithic | 1 |

###### 1440

###### 1441
Total RAM

###### 1442
No. of Devices

###### 1443
Device Type

###### 1444
No. of Ranks per Controller

###### 1445

###### 1446
8 GBytes

###### 1447
9

###### 1448
8Gbit monolithic

###### 1449
1

###### 1450

###### 1451
8 GBytes

###### 1452
9

###### 1453
8Gbit twin-die

###### 1454
2

###### 1455

###### 1456

###### 1457
9

###### 1458
8Gbit monolithic

###### 1459
1

##### 668: Interface Speed
- Category: Heading

###### 669
The memory interface shall be capable of operating at 1600MT/s
- Category: Requirement
- Derived: False
- Safety: False
- Verification Details: [DT] Measure memory clock frequency [=half specified data rate]
  [PT] All Production tests run using specified memory frequency.
- Verification Method: Design Proving Test, Production Test

#### 444: Non-Volatile Memory
- Category: Heading

##### 445: NOR Flash (Program Memory)
- Category: Heading

###### 446
The SBC314C shall include 256MBytes of NOR FLASH memory.
- Category: Requirement
- Derived: False
- Safety: False
- Verification Details: Inspection of schematic and BOM
- Verification Method: Inspection

###### 827
The FLASH shall be implemented using a single 2GBit Cypress S70GL02GS12FHIV1 memory device.
- Category: Requirement
- Derived: True
- Derived Req Justification: Industrial grade FLASH to support memory requirements.
- Safety: False
- Verification Details: Inspection of schematic and BOM
- Verification Method: Inspection

###### 962
The part number of the FLASH device is S70GL02GS12FHIV1
.
- Category: Information

###### 872
The Infineon S70GL NOR FLASH devices shall contain page-based ECC protection that is transparent to software.
- Category: Requirement
- Derived: True
- Derived Req Justification: Functionality needed to support single event upset mitigation and reliability.
- Safety: False
- Verification Details: Analysis of component datasheet.
- Verification Method: Analysis

###### 671
The NOR FLASH memory is connected to the CPU using the Local Bus Interface.
- Category: Information

###### 964
The NOR FLASH memory data bus connection is 16 bits wide.
- Category: Information

##### 447: NAND Flash (Bulk Storage)
- Category: Heading

###### 448
The SBC314C shall include a Solid-State Disk (SSD) or equivalent bulk storage device.
- Category: Requirement
- Derived: False
- Safety: False
- Verification Details: Inspection of schematic and BOM
- Verification Method: Inspection

###### 449
The SSD shall utilize Single-Level-Cell (SLC) FLASH technology.
- Category: Requirement
- Derived: True
- Derived Req Justification: SLC is a ruggedized flash with robust temperature ratings and longer read/write cycle reliability than MLC.
- Safety: False
- Verification Details: Analysis of component datasheet.
- Verification Method: Analysis

###### 873
The SSD shall include ECC protection.
- Category: Requirement
- Derived: False
- Safety: True
- Verification Details: Analysis of component datasheet.
- Verification Method: Analysis

###### 450
The SBC314C shall support a 64GB NAND SSD.
- Category: Requirement
- Derived: False
- Safety: False
- Verification Details: Inspection of schematic and BOM.
  Analysis of component datasheets.
- Verification Method: Inspection, Analysis

###### 741
The interface to the bulk storage device shall be SATA.
- Category: Requirement
- Derived: False
- Safety: False
- Verification Details: Inspection of schematic and BOM.
  Analysis of component datasheets.
- Verification Method: Inspection, Analysis

###### 828
There are no minimum bandwidth requirements for the bulk storage device.
- Category: Information

###### 1117
The SSD is implemented using a Silicon Motion SM659GEC-CDZ-SPA31E device.
- Category: Information

##### 453: NVRAM
- Category: Heading

###### 454
The SBC314C shall include 256KB of non-volatile RAM.
- Category: Requirement
- Derived: False
- Safety: False
- Verification Details: Inspection of schematic and BOM.
  Analysis of component datasheets.
- Verification Method: Inspection, Analysis

###### 455
The NVRAM shall be implemented using a single 2Mbit Cypress SPI F-RAM, or other technology offering equivalent functionality.
- Category: Requirement
- Derived: False
- Safety: False
- Verification Details: Inspection of schematic and BOM.
  Analysis of component datasheets.
- Verification Method: Inspection, Analysis

###### 963
The part number of the NVRAM is FM25V20A-DG.
- Category: Information

###### 734
The NVRAM shall be capable of retaining data for 20 years minimum.
- Category: Requirement
- Derived: True
- Derived Req Justification: Reliability and longevity design decision.
- Safety: False
- Verification Details: Analysis of component datasheets.
- Verification Method: Analysis

###### 735
The NVRAM shall support at least 10000 write cycles.
- Category: Requirement
- Derived: True
- Derived Req Justification: Reliability and longevity design decision.
- Safety: False
- Verification Details: Analysis of component datasheets.
- Verification Method: Analysis

###### 672
The NVRAM shall be connected to the CPU using the Local Bus Interface.
- Category: Requirement
- Derived: True
- Derived Req Justification: Enables interfacing with the FGPA.
- Safety: False
- Verification Details: Inspection of schematic.
  Analysis of component datasheets.
- Verification Method: Inspection, Analysis

###### 2097
The SBC314C shall store card level configuration information, including MAC address and board serial number, in NVRAM.
- Category: Requirement
- Derived: False
- Safety: False

###### 752
The NVRAM's read and write bandwidth and latencies are not specified.
- Category: Information

##### 456: Write Protection
- Category: Heading

###### 457
The SBC314C shall include WE (Write Enable) inputs from the TAC card connector to override write protection for the following Non-Volatile Memory devices:
U17 NVRAM, U74 NOR FLASH
Note:
WE for NOR FLASH = input signal FLASH_PW_UNLOCK_L
WE for NVRAM = input signal NVRAM_WE_LINK_L
- Category: Requirement
- Derived: True
- Derived Req Justification: Enables write protection at the board level, regardless of the state of the input signal, as a means to protect the memory.
- Safety: False
- Verification Details: Inspection of schematic.
  Analysis of component datasheets.
- Verification Method: Inspection, Analysis

###### 673
The lower 64 KB of NVRAM shall be write-protected when the WE input from the TAC card connector is not active.
- Category: Requirement
- Derived: True
- Derived Req Justification: Enables write protection at the board level, regardless of the state of the input signal, as a means to protect the memory.
- Safety: False
- Verification Details: Inspection of schematic.
  Analysis of component datasheets.
  Board level testing.
- Verification Method: Inspection, Analysis, Design Proving Test

###### 674
The NOR FLASH shall be write-protected when the backplane NVMRO input signal is high, regardless of the state of the WE inputs from the TAC card connector.
- Category: Requirement
- Derived: False
- Safety: False
- Verification Details: Inspection of schematic.
  Analysis of component datasheets.
  Board level testing.
- Verification Method: Inspection, Analysis, Design Proving Test

###### 736
The state of the WE inputs from the TAC card connector and the backplane NVMRO input shall be readable by software.
- Category: Requirement
- Derived: False
- Safety: False
- Verification Details: Inspection of schematic.
  Analysis of component datasheets.
  Board level testing.
- Verification Method: Inspection, Analysis, Design Proving Test

###### 1246
The NOR FLASH write enable input from the TAC card connector shall be active when a TAC card is not fitted.
Note: This will be accomplished with appropriate pull up/down resistors.
- Category: Requirement
- Derived: False
- Safety: False
- Verification Details: Inspection of schematic and hardware.
- Verification Method: Inspection

###### 2157
The lower 64 kB of NVRAM shall be write enabled when SW writes the NVRAM Unlock Password to FPGA register CFG_PASSWORD.
- Category: Requirement
- Derived: True
- Derived Req Justification: Allow ability to save config for U-Boot and VxWorks and Cert Bootloaders OS in pREP area.
- Safety: False

###### 2158
The lower 64 kB of NVRAM shall be write protected when SW writes the NVRAM Lock Password to FPGA register CFG_PASSWORD.
- Category: Requirement
- Derived: True
- Derived Req Justification: Allow ability to save config for U-Boot and VxWorks and Cert Bootloaders OS in pREP area.
- Safety: False

###### 676
Any software configuration (e.g. sector locking) required to achieve full write-protection shall be documented in the product reference manual.
- Category: Documentation Requirement
- Derived: True
- Derived Req Justification: Documentation support for in-service use.
- Safety: False
- Verification Details: Inspection of product reference manual.
- Verification Method: Inspection

##### 830: Write Protection (NOR FLASH Program Memory)
- Category: Heading

###### 835
The NOR FLASH program memory used on the SBC314C contains comprehensive, password-based, software sector locking features, as well as hardware write protection for the first and/or last sectors.
- Category: Information

###### 834
The SBC314C shall provide a means for software to retrieve the NOR Program Memory write protection password.
- Category: Requirement
- Derived: True
- Derived Req Justification: Helps enable software controlled access.
- Safety: False
- Verification Details: Inspection of schematic and BOM.
  Analysis of component datasheets.
  Analysis of FPGA design.
- Verification Method: Inspection, Analysis

###### 739
The password retrieval scheme for the NOR FLASH shall also have a software controlled interlock.
- Category: Requirement
- Derived: True
- Derived Req Justification: Provides tri-phase interlocking scheme for high levels of security.
- Safety: False
- Verification Details: Inspection of schematic and BOM.
  Analysis of component datasheets.
  Analysis of FPGA design.
- Verification Method: Inspection, Analysis

###### 1827
The NOR FLASH password retrieval shall only be enabled when all three locks are released (i.e. WE input from TAC card connector active, NVMRO low, software interlock opened).
- Category: Requirement
- Derived: True
- Derived Req Justification: Provides tri-phase interlocking scheme for high levels of security.
- Safety: False
- Verification Details: Inspection of schematic and BOM.
  Analysis of component datasheets.
  Analysis of FPGA design.
- Verification Method: Inspection, Analysis

###### 852
After boot has completed, backplane input pin GPIO_VPX5 shall emulate the operation of the NOR FLASH WE input from the TAC card connector.
- Category: Requirement
- Derived: True
- Derived Req Justification: Support Data Load function associated with GPIO5.
- Safety: False
- Verification Details: Inspection of schematic and BOM.
  Analysis of component datasheets.
  Analysis of FPGA design.
- Verification Method: Inspection, Analysis

##### 912: Retention
- Category: Heading

###### 913
All non-volatile devices on the SBC314C shall retain their data for a minimum of 20 years
- Category: Requirement
- Derived: True
- Derived Req Justification: 20 years supports reliability targets for the design's field-use objective.
- Safety: False
- Verification Details: Inspection of schematic and BOM.
  Analysis of component datasheets.
- Verification Method: Inspection, Analysis

#### 960: Local Bus Memory Map
- Category: Heading

##### 961
Chip selects for Local Bus Access shall be as follows:
- Category: Requirement
- Derived: True
- Derived Req Justification: Design decision.
- Safety: False
- Verification Method: Analysis

##### 1462
| Local Bus Chip Select | Target | Device Width | Required Window Size |
| --- | --- | --- | --- |
| CS0 | (Top half) NOR FLASH - Boot area (2x8MB) (Bottom half) Reset Control Word (inFGPA) | 16 | >=32MByte |
| CS1 | NOR FLASH | 16 | 256MBytes |
| CS2 | NVRAM | 8 | 256kBytes |
| CS3 | FGPA registers | 8 | 512kBytes |
| CS4 | Not used |  |  |
| CS5 | Not used |  |  |
| CS6 | Not used |  |  |
| CS7 | Not used |  |  |

###### 1463

###### 1464
Local Bus Chip Select

###### 1465
Target

###### 1466
Device Width

###### 1467
Required Window Size

###### 1468

###### 1469
CS0

###### 1470
(Top half)
NOR FLASH - Boot area (2x8MB)
(Bottom half)
Reset Control Word (inFGPA)

###### 1471
16

###### 1472
>=32MByte

###### 1473

###### 1474
CS1

###### 1475
NOR FLASH

###### 1476
16

###### 1477
256MBytes

###### 1478

###### 1479
CS2

###### 1480
NVRAM

###### 1481
8

###### 1482
256kBytes

###### 1483

###### 1484
CS3

###### 1485
FGPA registers

###### 1486
8

###### 1487
512kBytes

###### 1488

###### 1489
CS4

###### 1490
Not used

###### 1491

###### 1492

###### 1493

###### 1494
CS5

###### 1495
Not used

###### 1496

###### 1497

###### 1498

###### 1499
CS6

###### 1500
Not used

###### 1501

###### 1502

###### 1503

###### 1504
CS7

###### 1505
Not used

###### 1506

###### 1507

##### 1134: Boot Areas in NOR FLASH
- Category: Heading

###### 1133
The SBC314C shall support a 16MByte Boot Area, overlaid at the top of the NOR FLASH.
- Category: Requirement
- Derived: True
- Derived Req Justification: Design choice for size of boot firmware.
- Safety: False
- Verification Details: Inspection of schematic and BOM.
  Analysis of component datasheets.
  Analysis of FPGA design.
- Verification Method: Inspection, Analysis

###### 1136
All boot selection discretes shall be readable by software.
- Category: Requirement
- Derived: True
- Derived Req Justification: Allows SW to implement the needed Safety and Security (image verify) features during boot.
- Safety: False
- Verification Details: Inspection of schematic and BOM.
  Analysis of component datasheets.
  Analysis of FPGA design.
- Verification Method: Inspection, Analysis

###### 1828
The SBC314C shall provide mechanisms to swap the two areas ('Main' and 'Recovery') in the memory map.
- Category: Requirement
- Derived: True
- Derived Req Justification: Allows multiple Boot images to be stored.
- Safety: False
- Verification Details: Inspection of schematic and BOM.
  Analysis of component datasheets.
  Analysis of FPGA design.
- Verification Method: Inspection, Analysis

###### 1135
When the CPU executes boot code from the NOR FLASH, it uses CS0.
- Category: Information

###### 2108
CS0 shall be confined to an 8Mbyte address range.
- Category: Requirement
- Derived: True
- Derived Req Justification: Supports boot image access.
- Safety: False

###### 2107
The entire NOR FLASH shall be accessbile linearly through CS1.
- Category: Requirement
- Derived: True
- Derived Req Justification: Supports memory access during boot.
- Safety: False

###### 2109
When the 'main' boot area is selected, CS0 shall be overlaid at CS1+(248->256MB).
- Category: Requirement
- Derived: True
- Derived Req Justification: Supports main boot image access.
- Safety: False

###### 2110
When the 'recovery' boot area is selected, CS0 shall be overlaid at CS1+(240->248MB).
- Category: Requirement
- Derived: True
- Derived Req Justification: Support recovery boot area access.
- Safety: False

#### 1254: Recovery Boot
- Category: Heading

##### 1255
The SBC314C shall indicate request for recovery boot when it senses the following pattern on the GPIO7 VPX backplane pin:
(All times are +/- 100 us);
1) Open for 200 ms
2) GND for 50 ms
3) Open for 50 ms
4) GND for 50 ms
5) Open for 25 ms
6) GND for 25 ms
7) Open for 25 ms
8) GND for 50 ms
9) Open for 25 ms
10) GND for 50 ms
11) Open for 200 ms
- Category: Requirement
- Derived: False
- Safety: False
- Verification Details: Inspection of schematic and BOM.
  Analysis of component datasheets.
  Analysis of FPGA design.
- Verification Method: Inspection, Analysis

### 538: Hi-speed Fabric Interconnect
- Category: Heading

#### 677: Technology
- Category: Heading

##### 679
The SBC314C shall use PCI Express (PCIe) for high-speed interconnects, except where specified elsewhere
- Category: Requirement
- Derived: False
- Safety: False
- Verification Details: Inspection of schematic and BOM.
  Analysis of component datasheets.
  Analysis of FPGA design.
- Verification Method: Inspection, Analysis

##### 1190
The PCIe data bus hardware SHALL implement error detection and correction capability.
- Category: Requirement
- Derived: False
- Safety: True
- Verification Method: Design Proving Test

##### 1191
The PCIe data bus hardware SHALL support transient data fault correction using retry.
- Category: Requirement
- Derived: False
- Safety: True
- Verification Method: Analysis

##### 1192
The PCIe bus transceiver hardware SHALL be capable of detecting and reporting the loss of bus.
- Category: Requirement
- Derived: False
- Safety: True
- Verification Method: Analysis

##### 1193
The PCIe bus transceiver hardware SHALL be capable of detecting and reporting the loss of message.
- Category: Requirement
- Derived: False
- Safety: True
- Verification Method: Analysis

##### 1194
The PCIe bus transceiver hardware SHALL be capable of detecting and reporting the message bit errors.
- Category: Requirement
- Derived: False
- Safety: True
- Verification Method: Analysis

#### 678: Central Switch
- Category: Heading

##### 680
The SBC314C shall support a PLX PEX8619 16-lane PCIe switch
- Category: Requirement
- Derived: True
- Derived Req Justification: Component choice that supports required PCI functionality.
- Safety: False
- Verification Details: Inspection of schematic and BOM.
  Analysis of component datasheets.
- Verification Method: Inspection, Analysis

##### 971: Lane/Port Allocation
- Category: Heading

###### 972
The PCIe switch lane and port allocation shall be as shown in the table below.
See also section 4.1.1.1 'Port Combinations' table 4-1 in PEX8619 data book.
- Category: Requirement
- Derived: True
- Derived Req Justification: Design choice.
- Safety: False
- Verification Details: Analysis of component datasheets.
- Verification Method: Analysis

###### 1510
| Port No. | Lanes | Port Width | Link To | Lane Reverse | Dir |
| --- | --- | --- | --- | --- | --- |
| ALL CONFIGS |  |  |  |  |  |
| 0 | 0-3 | 4 | CPU | N | Up |
| 13 | 14 | 1 | Not used | N/A | Down |
| 11 | 13 | 1 | SATA bridge | N/A | Down |
| 3, 15 | 12, 15 | 2 | Not used | N/A | Down |
| 2x4 CONFIG - STRAP_PORTCFG = 3 |  |  |  |  |  |
| 1 | 8-11 | 4 | Backplane A | N | Down/NT |
| 2 | 4-7 | 4 | Backplane B | N | Down/NT |

###### 1511

###### 1512
Port No.

###### 1513
Lanes

###### 1514
Port Width

###### 1515
Link To

###### 1516
Lane Reverse

###### 1517
Dir

###### 1518

###### 1519
ALL CONFIGS

###### 1525

###### 1526
0

###### 1527
0-3

###### 1528
4

###### 1529
CPU

###### 1530
N

###### 1531
Up

###### 1532

###### 1533
13

###### 1534
14

###### 1535
1

###### 1536
Not used

###### 1537
N/A

###### 1538
Down

###### 1539

###### 1540
11

###### 1541
13

###### 1542
1

###### 1543
SATA bridge

###### 1544
N/A

###### 1545
Down

###### 1546

###### 1547
3, 15

###### 1548
12, 15

###### 1549
2

###### 1550
Not used

###### 1551
N/A

###### 1552
Down

###### 1553

###### 1554
2x4 CONFIG - STRAP_PORTCFG = 3

###### 1560

###### 1561
1

###### 1562
8-11

###### 1563
4

###### 1564
Backplane A

###### 1565: N

###### 1566
Down/NT

###### 1567

###### 1568
2

###### 1569
4-7

###### 1570
4

###### 1571
Backplane B

###### 1572
N

###### 1573
Down/NT

##### 683: Backplane Links
- Category: Heading

###### 981
The SBC314C backplane PCIe links are all connected directly to the on-board PCIe switch
- Category: Information

###### 540
The SBC314C shall support 8 lanes of PCIe fabric to the VPX backplane
- Category: Requirement
- Derived: False
- Safety: False
- Verification Details: Analysis of schematic, board layout, componenet data sheets.
  Pre & Post route signal integrety analysis.
  Board level hardware testing.
- Verification Method: Analysis, Design Proving Test

###### 541
The default configuration of the backplane fabric shall be 2 ports x 4 lanes, all lanes configured as downstream ports, CPU as PCIe Root Complex
- Category: Requirement
- Derived: False
- Safety: False
- Verification Details: Inspection of PCIe switch configuration code.
  Analysis of componenet datasheets.
- Verification Method: Inspection, Analysis

###### 542
The backplane fabric shall support a 1x4 plus 4x1 configuration option
- Category: Requirement
- Derived: True
- Derived Req Justification: Design decision to facilitate configuration options.
- Safety: False
- Verification Details: Inspection of schematic.
  Pre & Post route signal integrety analysis.
  Board level test.
- Verification Method: Inspection, Analysis, Design Proving Test

###### 543
The backplane fabric shall support an 8x1 configuration option
- Category: Requirement
- Derived: True
- Derived Req Justification: Design decision to facilitate configuration options.
- Safety: False
- Verification Details: Inspection of schematic.
  Pre & Post route signal integrety analysis.
  Board level test.
- Verification Method: Inspection, Analysis, Design Proving Test

###### 544
The SBC314C shall support a DMA controller that can access the backplane fabric interface
- Category: Requirement
- Derived: True
- Derived Req Justification: Required to support PCIe access.
- Safety: False
- Verification Details: Inspection of schematic and BOM.
  Analysis of component data sheets.
  Board level testing.
- Verification Method: Inspection, Analysis, Design Proving Test

###### 687
The backplane fabric shall operate at Gen1 (2.5Gbps) and Gen2 (5Gbps) speeds
- Category: Requirement
- Derived: False
- Safety: False
- Verification Details: Inspection of schematic.
  Pre & Post route signal integrety analysis.
  Board level test.
- Verification Method: Inspection, Analysis, Design Proving Test

###### 984
The PCIe reference clock uses d.c.-coupled CML signaling levels
- Category: Information

##### 973: Switch Configuration Methods
- Category: Heading

###### 974: Strapping
- Category: Heading

###### 975
The PCIe switch power-on configuration is set by pin straps that shall be configured as detailed in the table below:
- Category: Requirement
- Derived: True
- Derived Req Justification: Implementation decision.
- Safety: False
- Verification Details: Inspection of schematic and BOM.
  Analysis of component data sheets.
  Board level testing.
- Verification Method: Inspection, Analysis, Design Proving Test

###### 1684
| Strap Name | Setting | Result | Comment |
| --- | --- | --- | --- |
| DEBUG_SEL0 | 1 | PLX Reserved | - |
| FAST_BRINGUP# | 1 | PLX Reserved | - |
| NT_ENABLE# | 1 | Nt Disabled | - |
| NT_P2P_EN# | 1 | NT Peer-to-peer disabled | - |
| NT_UPSTRM_PORTSEL[3:0] | 1111 | NT Upstream port = 15 | [Data sheet requires port 15 when NT is disabled] |
| PLL_BYPASS# | 1 | PLX Reserved | - |
| PORTCFG[3:0] | 0011 | 3x4 + 4x1 | CPU and backplane links all x4, others x1. See table above. |
| PROBE_MOD# | 1 | PLX Reserved | - |
| RESERVED17# | 1 | PLX Reserved | - |
| RESERVED16 | 0 | PLX Reserved | - |
| SERDES_MODE_EN# | 1 | PLX Reserved | - |
| SMBUS_EN# | 1 | Master I2C bus not used | - |
| SPARE[5,1,0]# | 111 | PLX Reserved | - |
| SSC_ISO_ENABLE# | 1 | Spread spectrum clock not used | - |
| TESTMODE[3:0] | 1111 | PLX Reserved | - |
| UPCFG_TIMER_EN# | 1 | Upconfig timer disabled | - |
| UPSTRM_PORTSEL[3:0] | 0000 | CPU is mainstream port | - |

###### 1685

###### 1686
Strap Name

###### 1687
Setting

###### 1688
Result

###### 1689
Comment

###### 1690

###### 1691
DEBUG_SEL0

###### 1692
1

###### 1693
PLX Reserved

###### 1694
-

###### 1695

###### 1696
FAST_BRINGUP#

###### 1697
1

###### 1698
PLX Reserved

###### 1699
-

###### 1700

###### 1701
NT_ENABLE#

###### 1702
1

###### 1703
Nt Disabled

###### 1704
-

###### 1705

###### 1706
NT_P2P_EN#

###### 1707
1

###### 1708
NT Peer-to-peer disabled

###### 1709: -

###### 1710

###### 1711
NT_UPSTRM_PORTSEL[3:0]

###### 1712
1111

###### 1713
NT Upstream port = 15

###### 1714
[Data sheet requires port 15 when NT is disabled]

###### 1715

###### 1716
PLL_BYPASS#

###### 1717
1

###### 1718
PLX Reserved

###### 1719
-

###### 1720

###### 1721
PORTCFG[3:0]

###### 1722
0011

###### 1723
3x4 + 4x1

###### 1724
CPU and backplane links all x4, others x1. See table above.

###### 1725

###### 1726
PROBE_MOD#

###### 1727
1

###### 1728
PLX Reserved

###### 1729
-

###### 1730

###### 1731
RESERVED17#

###### 1732
1

###### 1733
PLX Reserved

###### 1734
-

###### 1735

###### 1736
RESERVED16

###### 1737
0

###### 1738
PLX Reserved

###### 1739
-

###### 1740

###### 1741
SERDES_MODE_EN#

###### 1742
1

###### 1743
PLX Reserved

###### 1744
-

###### 1745

###### 1746
SMBUS_EN#

###### 1747
1

###### 1748
Master I2C bus not used

###### 1749
-

###### 1750

###### 1751
SPARE[5,1,0]#

###### 1752
111

###### 1753
PLX Reserved

###### 1754
-

###### 1755

###### 1756
SSC_ISO_ENABLE#

###### 1757
1

###### 1758
Spread spectrum clock not used

###### 1759
-

###### 1760

###### 1761
TESTMODE[3:0]

###### 1762
1111

###### 1763
PLX Reserved

###### 1764
-

###### 1765

###### 1766
UPCFG_TIMER_EN#

###### 1767
1

###### 1768
Upconfig timer disabled

###### 1769
-

###### 1770

###### 1771
UPSTRM_PORTSEL[3:0]

###### 1772
0000

###### 1773
CPU is mainstream port

###### 1774
-

###### 977: I2C slave interface
- Category: Heading

###### 546
The central PCIe switch shall include an I2C slave interface for configuration by the CPU
- Category: Requirement
- Derived: True
- Derived Req Justification: Enables CPU controlled configuration of PCIe switch.
- Safety: False
- Verification Details: Inspection of schematic and BOM.
  Analysis of component data sheets.
  Board level testing.
- Verification Method: Inspection, Analysis, Design Proving Test

#### 682: CPU Links
- Category: Heading

##### 684
The SBC314C shall support a 4 lane link between the CPU and the PCIe switch
- Category: Requirement
- Derived: False
- Safety: False
- Verification Details: Inspection of schematic and BOM.
  Analysis of component data sheets.
  Board level testing.
- Verification Method: Inspection, Analysis, Design Proving Test

##### 686
The CPU/switch link shall use PCIe lanes 0-3 on the CPU.
- Category: Requirement
- Derived: True
- Derived Req Justification: Design decision.
- Safety: False
- Verification Details: Inspection of schematic and BOM.
  Analysis of component data sheets.
- Verification Method: Inspection, Analysis

##### 685
The link from the CPU to the PCIe switch shall operate at Gen2 speed (5GT/s).
- Category: Requirement
- Derived: False
- Safety: False
- Verification Details: Inspection of schematic and BOM.
  Analysis of component data sheets.
  Pre & Post route signal integrety analysis.
  Board level testing.
- Verification Method: Inspection, Analysis, Design Proving Test

##### 949
The CPU also includes a 2nd 4 lane link which is dedicated to the mezzanine site. See 'Mezzanines' section for further details.
- Category: Information

### 479: I/O Features
- Category: Heading

#### 1835
The SBC314C shall reject pulses shorter than 10 ms on any I/O who's frequency is not governed by an industry communication bus standard.
- Category: Requirement
- Derived: True
- Derived Req Justification: General I/O discretes require debounce for fault tolerant functionality.
- Safety: False
- Verification Details: Board level testing.
- Verification Method: Production Test

#### 480: Ethernet
- Category: Heading

##### 689: 1000Base-T options
- Category: Heading

###### 481
The SBC314C shall support two 1000BASE-T Ethernet channels
- Category: Requirement
- Derived: False
- Safety: False
- Verification Details: Inspection of schematic and BOM.
  Analysis of component data sheets.
  Pre & Post route signal integrety analysis.
  Board level testing.
- Verification Method: Inspection, Analysis, Design Proving Test

###### 905
All BASE-T Ethernet channels shall be transformer coupled
- Category: Requirement
- Derived: True
- Derived Req Justification: The isolation transformers for all Base-T ethernet will be provided on the board itself. This is a standard design practice and customer expectation for all our SBCs.
- Safety: False
- Verification Details: Inspection of schematic and BOM.
  Analysis of component data sheets.
- Verification Method: Inspection, Analysis

###### 798
All 1000BASE-T Ethernet ports shall also support 10 BASE-T and 100 BASE-TX operating modes.
- Category: Requirement
- Derived: True
- Derived Req Justification: Provides backwards compatibility with earlier Ethernet standards.
- Safety: False
- Verification Details: Inspection of schematic and BOM.
  Analysis of component data sheets.
  Pre & Post route signal integrety analysis.
  Board level testing.
- Verification Method: Inspection, Analysis, Design Proving Test

###### 691
The two 1000Base-T Ethernet ports shall use the Ethernet pinout defined by OpenVPX module profile MOD3-PAY-2F2T-16.2.5-3
- Category: Requirement
- Derived: False
- Safety: False
- Verification Method: Inspection

##### 487: IEEE1588
- Category: Heading

###### 488
All Ethernet channels shall support the IEEE1588 precision timestamp protocol
- Category: Requirement
- Derived: True
- Derived Req Justification: Ensures accurate synchronization across Ethernet channels.
- Safety: False
- Verification Method: Analysis

##### 757: Testability
- Category: Heading

###### 758
All Ethernet channels shall include a loopback feature within the appropriate PHY
- Category: Requirement
- Derived: True
- Derived Req Justification: Supports system testing.
- Safety: False
- Verification Method: Analysis

##### 760: Link Status
- Category: Heading

###### 761
All Ethernet channels shall include a means for software to monitor the link status
- Category: Requirement
- Derived: False
- Safety: True
- Verification Method: Analysis

##### 987: Implementation Details
- Category: Heading

###### 989: Ports 0 and 1
- Category: Heading

###### 988
Ethernet ports 0 and 1 utilize the MAC components that are built into the host processor
- Category: Information

###### 990
Ports 0 and 1 incorporate Marvell 88E1512 physical layer interfaces (PHYs), one per port. The 88E1512 can be configured to operate in 1000Base-T mode.
- Category: Information

###### 991
The PHYs are connected to the processor MACs using the RGMII protocol and signaling
- Category: Information

###### 1010
The PHY management interface on both PHYs is connected to the ETH0 management interface of the processor
- Category: Information

###### 1122
The PHY addresses on the management interface are set to 0 and 1 respectively.
- Category: Information

##### 1001: MOD3-PAY-2F2T-16.2.5-3
- Category: Heading

###### 1002
Ethernet ports 0 and 1 are configured as 1000Base-T and appear in the standard Control Plane locations defined by the Module Profile.
- Category: Information

#### 489: USB2.0
- Category: Heading

##### 490
The SBC314C shall support 2 USB2.0 host ports.
- Category: Requirement
- Derived: False
- Safety: False
- Verification Method: Inspection

##### 994
The USB2 host ports are provided by on-chip controllers within the host processor.
- Category: Information

##### 698
Each USB2.0 host port shall provide a dedicated, current-limited power pin supplying at least 0.5A.
- Category: Requirement
- Derived: True
- Derived Req Justification: 0.5A from USB 2.0
- Safety: False
- Verification Method: Inspection

##### 995
The USB2 host port power rails shall be provided by a Texas Instruments TPS2064. The per-port power control and overcurrent fault detection signals are wired back to the CPU and are available in the host port controller blocks.
- Category: Requirement
- Derived: True
- Derived Req Justification: Design choice to support USB requirements.
- Safety: False
- Verification Method: Inspection

##### 1244
The USB2.0 host ports shall be capable of running at 480 Mbps.
- Category: Requirement
- Derived: False
- Safety: False
- Verification Method: Analysis

##### 2038
Note: The data rate for USB2.0 is 480Mbps, however, once the overhead for data transfer protocols is accounted for (framing information, packet information, reserved time & clock adjustment), actual data transfer is closer to 320Mbps.
- Category: Information

#### 491: SATA
- Category: Heading

##### 492
The SBC314C shall support 2 SATA ports; one to an on-board SSD and one to the VPX backplane.
- Category: Requirement
- Derived: False
- Safety: False
- Verification Method: Inspection

##### 493
The SATA ports shall support operation at SATA 2.0 speeds (3Gbps).
- Category: Requirement
- Derived: False
- Safety: False
- Verification Method: Analysis

##### 1005: Implementation
- Category: Heading

###### 1006
A Marvell 88SE9170A2-NNX2I000 PCIe SATA controller shall be used to implement the 2 SATA ports. It is connected back to the CPU via the central PCIe switch.
- Category: Requirement
- Derived: True
- Derived Req Justification: Design choice to support SATA requirements.
- Safety: False
- Verification Method: Inspection

###### 1008
Port 1 on the SATA controller shall be dedicated to the on-board NAND FLASH SSD.
- Category: Requirement
- Derived: True
- Derived Req Justification: Design choice.
- Safety: False
- Verification Details: Inspection of schematic and BOM.
  Analysis of component datasheets.
- Verification Method: Inspection, Analysis

###### 1829
Port 0 on the SATA controller shall be dedicated to the VPX connector.
- Category: Requirement
- Derived: True
- Derived Req Justification: Design choice.
- Safety: False
- Verification Details: Inspection of schematic and BOM.
  Analysis of component datasheets.
- Verification Method: Inspection, Analysis

###### 2036

#### 496: Serial Ports
- Category: Heading

##### 497
The SBC314C shall support 2 asynchronous serial ports with CTS/RTS handshaking.
- Category: Requirement
- Derived: False
- Safety: False
- Verification Details: Inspection of schematic and BOM.
  Analysis of component datasheets.
- Verification Method: Analysis, Design Proving Test

##### 762
The serial port transceivers shall include a loopback mode which returns CPU transmit data back to the CPU receiver.
- Category: Requirement
- Derived: True
- Derived Req Justification: Supports system tests.
- Safety: False
- Verification Details: Inspection of schematic and BOM.
  Analysis of component datasheets.
  Board level test.
- Verification Method: Inspection, Analysis, Design Proving Test

##### 804
The serial ports are implemented using the UARTs built into the CPU. These are interrupt driven, and provide a limited amount of support for auto-handshaking.
- Category: Information

##### 811
The serial ports' data transmission rates shall be software configurable.
- Category: Requirement
- Derived: True
- Derived Req Justification: Necessary to configure the ports through the software.
- Safety: False
- Verification Details: Inspection of schematic and BOM.
  Analysis of component datasheets.
  Board level test.
- Verification Method: Inspection, Analysis, Design Proving Test

##### 812
All serial ports shall be capable of simultaneous operation.
- Category: Requirement
- Derived: True
- Derived Req Justification: Implementation decision.
- Safety: False
- Verification Details: Inspection of schematic and BOM.
  Analysis of component datasheets.
  Board level test.
- Verification Method: Inspection, Analysis, Design Proving Test

##### 813
Serial port throughput performance shall be characterised, in particular any reduction that may occur as a result of using multiple serial interfaces at the same time.
- Category: Requirement
- Derived: True
- Derived Req Justification: Ensures port performance can be monitored.
- Safety: False
- Verification Details: Pre and Post route signal integrety analysis.
  Board level test.
- Verification Method: Analysis, Design Proving Test

##### 806: Fault Tolerance
- Category: Heading

###### 807
The SBC shall not be damaged by any external short occurring between any individual serial port signal and signal return.
- Category: Requirement
- Derived: True
- Derived Req Justification: Good design practice for reliability and fault tolerance.
- Safety: False
- Verification Details: Inspection of schematic and BOM.
  Analysis of component datasheets.
  Board level test.
- Verification Method: Inspection, Analysis, Design Proving Test

###### 808
For differential signal interfaces, the SBC shall not be damaged by any external short occurring between the two legs of any channel pair.
- Category: Requirement
- Derived: True
- Derived Req Justification: Good design practice for reliability and fault tolerance.
- Safety: False
- Verification Method: Design Proving Test

###### 809
The presence of any fault in this section shall not affect any other part of the SBC outside the serial channel with the fault.
- Category: Requirement
- Derived: True
- Derived Req Justification: Good design practice for reliability and fault tolerance.
- Safety: False
- Verification Method: Design Proving Test

###### 810
The serial interface channel shall return to normal operation after removal of any external fault described in this section.
- Category: Requirement
- Derived: True
- Derived Req Justification: Good design practice for reliability and fault tolerance.
- Safety: False
- Verification Method: Design Proving Test

##### 498: RS232
- Category: Heading

###### 499
Each serial port shall support RS232 operation in the default build option.
- Category: Requirement
- Derived: True
- Derived Req Justification: Design decision.
- Safety: False
- Verification Details: Inspection of schematic and BOM for the default build.
  Analysis of datasheets.
  Board level test.
- Verification Method: Inspection, Analysis, Design Proving Test

###### 902
The RS232 serial ports shall comply with TIA/EIA-232.
- Category: Requirement
- Derived: False
- Safety: False
- Verification Details: Inspection of schematic and BOM for the default build.
  Analysis of datasheets.
  Board level test.
- Verification Method: Inspection, Analysis, Design Proving Test

###### 904
The RS232 serial ports shall support standard baud rates between 4.8 Kbps and 115.2 Kbps.
- Category: Requirement
- Derived: False
- Safety: False
- Verification Details: Pre and post route signal integrety analysis.
  Board level test.
- Verification Method: Analysis, Design Proving Test

###### 500
In RS232 mode, the SBC314C shall support 2x 4-wire asynchronous serial ports, with hardware handshaking (CTS/RTS).
- Category: Requirement
- Derived: False
- Safety: False
- Verification Method: Inspection, Analysis

###### 903
The RS232 transceivers shall implement 'bus quiet' protection receivers so that the input line state is held in a known state when the input is high-impedance or not connected.
- Category: Requirement
- Derived: True
- Derived Req Justification: Good design practice.
- Safety: False
- Verification Method: Design Proving Test

##### 1013: Implementation Details
- Category: Heading

###### 1014
The transceiver used shall be the Intersil ISL41334. One chip supports all 8 external wires.
- Category: Requirement
- Derived: True
- Derived Req Justification: Component implementation choice.
- Safety: False
- Verification Details: Inspection of schematic and BOM.
- Verification Method: Inspection

#### 503: General Purpose I/O (GPIO)
- Category: Heading

##### 504
The SBC314C shall support 8 GPIO signals.
- Category: Requirement
- Derived: False
- Safety: False
- Verification Method: Inspection

##### 800
The GPIO signals shall use 3.3V LVCMOS signaling.
- Category: Requirement
- Derived: True
- Derived Req Justification: Consistent with board level design.
- Safety: False
- Verification Method: Analysis

##### 801
The GPIO signals shall support open-drain signaling when configured in output mode.
- Category: Requirement
- Derived: False
- Safety: False
- Verification Method: Inspection

##### 1022
The GPIO signals shall be configured using FPGA I/O pin pullups.
[External pullups to P3V3_AUX are recommended if the system design uses open-drain signaling]
- Category: Requirement
- Derived: True
- Derived Req Justification: The FPGA provides internal, user selectable pullups. Using the internal pullups reduces part count and cost.
- Safety: False
- Verification Method: Inspection, Design Proving Test

##### 506
The GPIO signals shall be 5V tolerant.
- Category: Requirement
- Derived: True
- Derived Req Justification: Design choice
- Safety: False
- Verification Details: Inspection of schematic and BOM.
  Analysis of component datasheet.
  Board level test.
- Verification Method: Inspection, Analysis, Design Proving Test

##### 771
The GPIO shall allow test software to override the input value of any pin configured as an input.
- Category: Requirement
- Derived: True
- Derived Req Justification: Supports system testability.
- Safety: False
- Verification Details: Board level test.
- Verification Method: Design Proving Test

##### 1018: Implementation Details
- Category: Heading

###### 1019
The external GPIO functions are all implemented in the FPGA.
- Category: Information

###### 1020
A Texas Instruments 74CB3T3245 bi-directional buffer shall be provided between the FPGA and the backplane.
- Category: Requirement
- Derived: True
- Derived Req Justification: This protects the 3.3V FPGA from over-voltages (e.g. 5V) received from the backplane.
- Safety: False
- Verification Details: Inspection of schematic and BOM.
- Verification Method: Inspection

###### 1021
The buffer shall be disabled whenever a power failure is detected.
- Category: Requirement
- Derived: True
- Derived Req Justification: Prevents glitches during power-up.
- Safety: False
- Verification Method: Analysis

### 459: Mezzanines
- Category: Heading

#### 460: XMC
- Category: Heading

##### 461
The SBC314C shall support one single-width XMC Mezzanine site.
- Category: Requirement
- Derived: True
- Derived Req Justification: Design decision.
- Safety: False
- Verification Details: Inspection of schematic.
  Board level interop test.
- Verification Method: Inspection, Design Proving Test

##### 462
The XMC site shall be compliant with VITA42 for the standard build.
- Category: Mechanical Requirement
- Derived: True
- Derived Req Justification: A widely deployed mezzanine statndard for high reliability technology.
- Safety: False
- Verification Details: Inspection of schematic and BOM.
  Analysis of VITA42.
- Verification Method: Inspection, Analysis

##### 464
The XMC site fabric interface shall be PCI Express (PCIe).
- Category: Requirement
- Derived: False
- Safety: False
- Verification Details: Inspection of schematic and BOM.
  Analysis of component datasheet.
- Verification Method: Inspection, Analysis

##### 465
The XMC site fabric interface shall be at least 4 lanes wide.
- Category: Requirement
- Derived: False
- Safety: False
- Verification Details: Inspection of schematic.
- Verification Method: Inspection

##### 466
The XMC site fabric interface shall support PCIe Gen 2 operating speed.
- Category: Requirement
- Derived: False
- Safety: False
- Verification Details: Inspection of schematic and layout.
  Pre and Post route signal integrety analysis.
- Verification Method: Inspection, Analysis

##### 701
The PCIe fabric for the XMC site shall be connected to PCIe lanes 4-7 on the Integrated Host Processor.
- Category: Requirement
- Derived: True
- Derived Req Justification: Design decision.
- Safety: False
- Verification Details: Inspection of schematic and BOM.
  Analysis of component datasheet.
- Verification Method: Inspection, Analysis

##### 877
The state of the following XMC site J15 connections shall be available to host software: MRSTI_N, MRST_O, MPRESENT
- Category: Requirement
- Derived: True
- Derived Req Justification: Support software visibility of reset state.
- Safety: False
- Verification Details: Inspection of schematic.
  Board level test.
- Verification Method: Inspection, Design Proving Test

##### 878
The XMC site geographic address shall be fixed as zero.
- Category: Requirement
- Derived: True
- Derived Req Justification: Design decision
- Safety: False
- Verification Details: Inspection of schematic
- Verification Method: Inspection

###### 1029
The System Management (SM) bus to the XMC site interface is connected to the internal sensor I2C bus.
- Category: Information

##### 467
The XMC site user I/O interface shall comply with the VITA46.9 P2w1-X24s+X8d+X12d profile.
- Category: Requirement
- Derived: False
- Safety: False
- Verification Details: Inspection of schematic
- Verification Method: Inspection

##### 880
The XMC site user I/O interface shall use 78 ohm at 100kHz, differential routing, for the following differential pairs:
78 Ohm @ 100kHz
PMC_XMC_IO[ 1], PMC_XMC_IO[ 3]
PMC_XMC_IO[ 2], PMC_XMC_IO[ 4]
PMC_XMC_IO[ 6], PMC_XMC_IO[ 8]
PMC_XMC_IO[10], PMC_XMC_IO[12]
PMC_XMC_IO[17], PMC_XMC_IO[19]
PMC_XMC_IO[21], PMC_XMC_IO[23]
PMC_XMC_IO[25], PMC_XMC_IO[27]
PMC_XMC_IO[26], PMC_XMC_IO[28]
PMC_XMC_IO[29], PMC_XMC_IO[31]
PMC_XMC_IO[30], PMC_XMC_IO[32]
PMC_XMC_IO[49], PMC_XMC_IO[51]
PMC_XMC_IO[50], PMC_XMC_IO[52]
PMC_XMC_IO[54], PMC_XMC_IO[56]
PMC_XMC_IO[57], PMC_XMC_IO[59]
PMC_XMC_IO[58], PMC_XMC_IO[60]
PMC_XMC_IO[61], PMC_XMC_IO[63]
PMC_XMC_IO[62], PMC_XMC_IO[64]
- Category: Requirement
- Derived: False
- Safety: False
- Verification Details: Inspection of schematic, and layout.
  Pre and Post route signal integrety analysis.
- Verification Method: Inspection, Analysis

##### 1824
The XMC site user I/O interface shall use 78 ohm at 1MHz, differential routing, for the following differential pairs:
78 Ohm @ 1MHz
PMC_XMC_IO[33], PMC_XMC_IO[35]
PMC_XMC_IO[34], PMC_XMC_IO[36]
PMC_XMC_IO[37], PMC_XMC_IO[39]
PMC_XMC_IO[38], PMC_XMC_IO[40]
PMC_XMC_IO[41], PMC_XMC_IO[43]
PMC_XMC_IO[42], PMC_XMC_IO[44]
PMC_XMC_IO[45], PMC_XMC_IO[47]
PMC_XMC_IO[46], PMC_XMC_IO[48]
- Category: Requirement
- Derived: True
- Derived Req Justification: Allows for compatibility with 78 ohm differential lines.
- Safety: False
- Verification Details: Inspection of schematic, and layout.
  Pre and Post route signal integrety analysis.
- Verification Method: Inspection, Analysis

##### 881
The XMC site user I/O interface shall utilize 50 ohm single-ended routing for all signals defined as single ended.
- Category: Requirement
- Derived: False
- Safety: False
- Verification Details: Inspection of schematic, and layout.
  Pre and Post route signal integrety analysis.
- Verification Method: Inspection, Analysis

##### 1825
The following single ended traces shall be routed with 50 Ohm impedance supporting 500mA:
PMC_XMC_IO[14], [16], [18], [20], [22], [24]
- Category: Requirement
- Derived: True
- Derived Req Justification: Allows for compatibility with 50 traces.
- Safety: False
- Verification Details: Inspection of schematic, and layout.
  Pre and Post route signal integrety analysis.
- Verification Method: Inspection, Analysis

#### 475: Mezzanine Power
- Category: Heading

##### 476
The SBC314C shall be able to supply 25W to the mezzanine sites.
- Category: Requirement
- Derived: True
- Derived Req Justification: Design decision for power management.
- Safety: False
- Verification Details: Inspection of schematic, BOM, and layout.
  Analysis of componenet data sheets.
- Verification Method: Inspection, Analysis

##### 898
The SBC314C shall connect the +/-12V (auxiliary), 5V (Vs3) and 3.3V (Vs2) rails from the backplane to the mezzanine sites.
- Category: Requirement
- Derived: True
- Derived Req Justification: Required to power mezzanine boards.
- Safety: False
- Verification Details: Inspection of schematic
- Verification Method: Inspection

##### 1118
The SBC314C shall power up the main 5V and 3.3V power rails to the mezzanine at approximately the same time.
- Category: Requirement
- Derived: True
- Derived Req Justification: Ensure consistent power scheme.
- Safety: False
- Verification Details: Inspection of schematic and BOM.
  Analysis of component data sheets.
  Board level test.
- Verification Method: Inspection, Analysis, Design Proving Test

#### 477: Mezzanine Thermals
- Category: Heading

##### 478
The SBC314C cooling solution shall support mezzanines that dissipate up to 12.5W.
- Category: Mechanical Requirement
- Derived: True
- Derived Req Justification: Design decision for cooling capacity.
- Safety: False
- Verification Details: Analysis of mechanical design.
- Verification Method: Analysis

### 763: FPGA
- Category: Heading

#### 764
The SBC314C contains an FPGA device which implements various support functions, e.g. glue logic, reset control, voltage translation, timers, etc.
- Category: Information

#### 765: Technology
- Category: Heading

##### 766
The SBC314C FPGA shall be a Lattice MachXO2 family device.
- Category: Requirement
- Derived: True
- Derived Req Justification: Component decision that supports required functionality.
- Safety: False
- Verification Details: Inspection of schematic and BOM.
- Verification Method: Inspection

#### 775: Features
- Category: Heading

##### 1130: Identification and Revision Control
- Category: Heading

##### 922: Reset Configuration Word
- Category: Heading

###### 923
The SBC314C FPGA shall provide a 'reset configuration word' (RCW) to the CPU.
This is used to perform various chipset initialisation.
- Category: Requirement
- Derived: True
- Derived Req Justification: Required for supporting chipset initialization.
- Safety: False
- Verification Details: Inspection of FPGA code.
- Verification Method: Inspection

##### 855: Reset
- Category: Heading

###### 856
The SBC314C shall reset the CPU (PORESET) and all other on board circuits when a SYSRESET input is received from the backplane.
- Category: Requirement
- Derived: True
- Derived Req Justification: Supporting implementation specification for system reset.
- Safety: False
- Verification Details: Board level test.
- Verification Method: Design Proving Test

###### 1141
When configured as VPX system controller, the SBC314C shall drive the VPX SYSRESET backplane signal low when an on-board reset condition is asserted.
- Category: Requirement
- Derived: True
- Derived Req Justification: Supporting implementation specification for system reset.
- Safety: False
- Verification Details: Board level test.
- Verification Method: Design Proving Test

###### 1142
When configured to do so, the SBC314C shall drive the VPX SYSRESET backplane signal low when an on-board reset condition is asserted, regardless of whether it is system controller or not.
- Category: Requirement
- Derived: True
- Derived Req Justification: Supporting implementation specification for system reset.
- Safety: False
- Verification Details: Board level test.
- Verification Method: Design Proving Test

###### 857
When configured to do so, the SBC314C shall send a non-maskable interrupt to the CPU when the VPX_GDISC1 backplane signal is asserted.
- Category: Requirement
- Derived: True
- Derived Req Justification: Supporting implementation specification for system reset.
- Safety: False
- Verification Details: Board level test.
- Verification Method: Design Proving Test

###### 858
When configured to do so, the SBC314C shall reset the CPU (PORESET) when the Maskable Reset backplane signal is asserted.
- Category: Requirement
- Derived: True
- Derived Req Justification: Supporting implementation specification for system reset.
- Safety: False
- Verification Details: Board level test.
- Verification Method: Design Proving Test

###### 894
When configured to do so, the SBC314C shall reset all on board circuits when the Maskable Reset backplane signal is asserted.
- Category: Requirement
- Derived: True
- Derived Req Justification: Supporting implementation specification for system reset.
- Safety: False
- Verification Details: Board level test.
- Verification Method: Design Proving Test

###### 901
The default configuration of the SBC314C shall be to ignore the Maskable Reset backplane signal.
- Category: Requirement
- Derived: True
- Derived Req Justification: Supporting implementation specification for system reset.
- Safety: False
- Verification Details: Inspect processor and/or FPGA code.
  Board level test.
- Verification Method: Inspection, Design Proving Test

###### 859
The SBC314C shall incorporate a mechanism for application software to initiate a self-reset.
- Category: Requirement
- Derived: True
- Derived Req Justification: Supporting implementation specification for system reset.
- Safety: False
- Verification Details: Inspection of schematic and BOM.
  Analysis of component datasheet.
  Inspect processor and/or FPGA code.
  Board level test.
- Verification Method: Inspection, Analysis, Design Proving Test

###### 924
The SBC314C shall include a number of register bits that are not cleared upon a software initiated self-reset.
Note: These are intended for use by BIT and/or primary bootloaders, and are separate from the scratchpad storage referred to below, which is for application software use.
- Category: Requirement
- Derived: True
- Derived Req Justification: Allows bootloader and BIT registers to remain unchanged during reset.
- Safety: False
- Verification Details: Inspect FPGA code.
  Board level test.
- Verification Method: Inspection, Design Proving Test

###### 928
The BIT status registers described above shall be mirrored into the CPU Power-on Configuration Word (this is driven onto the IFC bus during power-on reset and appears in the DCFG_CCSR_GPPORCR1).
- Category: Requirement
- Derived: True
- Derived Req Justification: Allows bootloader and BIT registers to remain unchanged during reset.
- Safety: False
- Verification Details: Inspect FPGA code.
  Board level test.
- Verification Method: Inspection, Design Proving Test

###### 860
The SBC314C shall assert XMC RESET_IN when the backplane SYSRESET is asserted.
- Category: Requirement
- Derived: True
- Derived Req Justification: Supporting implementation specification for system reset.
- Safety: False
- Verification Details: Board level test.
- Verification Method: Design Proving Test

###### 861
When configured to do so, the SBC314C shall assert XMC RESET_IN when the GDiscrete1 backplane signal is asserted.
- Category: Requirement
- Derived: True
- Derived Req Justification: Supporting implementation specification for system reset.
- Safety: False
- Verification Details: Board level test.
- Verification Method: Design Proving Test

###### 1138
When configured to do so, the SBC314C shall assert XMC RESET_IN when the VPX Maskable reset backplane signal is asserted.
- Category: Requirement
- Derived: True
- Derived Req Justification: Supporting implementation specification for system reset.
- Safety: False
- Verification Details: Board level test.
- Verification Method: Design Proving Test

###### 863
The SBC314C shall record the reason for reset in a memory-mapped register that is accessible to software.
- Category: Requirement
- Derived: True
- Derived Req Justification: Support BIT functions.
- Safety: False
- Verification Details: Board level test.
- Verification Method: Design Proving Test

###### 864
The SBC314C shall set the serial ports and backplane GPIOs to the inactive state upon reset.
- Category: Requirement
- Derived: True
- Derived Req Justification: Implementation specification for system reset.
- Safety: False
- Verification Details: Board level test.
- Verification Method: Design Proving Test

##### 917: Scratchpad Storage
- Category: Heading

###### 918
The SBC314C shall incorporate a 1 byte scratchpad register that is NOT cleared upon reset
[This may be used by application software to record the reason for reset, or for any other function]
- Category: Requirement
- Derived: True
- Derived Req Justification: Support BIT function.
- Safety: False
- Verification Details: Inspection of FPGA code.
  Board level test.
- Verification Method: Inspection, Design Proving Test

###### 919
The SBC314C shall incorporate a 16 byte scratchpad memory that is NOT cleared or modified by any reset condition, except power up where it is cleared.
- Category: Requirement
- Derived: True
- Derived Req Justification: Support BIT functions.
- Safety: False
- Verification Details: Inspection of FPGA code.
  Board level test.
- Verification Method: Inspection, Design Proving Test

### 784: Power Manager
- Category: Heading

#### 787
The SBC314C shall incorporate a power manager.
- Category: Requirement
- Derived: True
- Derived Req Justification: Design decision to implement common design practice of power management.
- Safety: False
- Verification Details: Inspection of FPGA code.
- Verification Method: Inspection

#### 1034
The power manager I2C bus is connected to the FPGA and to the 'sensor' I2C bus.
- Category: Information

#### 2039: Power Sequence
- Category: Heading

##### 2042
For clarity, a flow diagram of the power sequencing system is shown below.
NB: The diagram indicates the high-level functionality of input and outputs -refer to the detailed requirements for exact signal names and behaviour.
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- Category: Requirement
- Derived: True
- Derived Req Justification: Staged power up is required for proper startup of the processor and it's periphals.
- Safety: False

##### 2043
The power sequencing system shall begin the power on sequence as soon as all backplane power rails (P5V, P3V3, P3V3_AUX) are in spec.
- Category: Requirement
- Derived: True
- Derived Req Justification: Power quality must be stable before initiating components.
- Safety: False

##### 2044
The signal BP_RAILS_OK shall be asserted when the power on sequence starts.
- Category: Requirement
- Derived: True
- Derived Req Justification: Necessary to signal the primary rails are in range.
- Safety: False

##### 2045
Once the power on sequence has started, the undervoltage monitors on the backplane power rails shall be ignored for 70ms.
- Category: Requirement
- Derived: True
- Derived Req Justification: This ensures inrush currents don't trigger a undervoltage condition during initial power delivery to components.
- Safety: False

##### 2046
Once the power on sequence has started, it shall automatically follow the power sequence shown in the above figure.
- Category: Requirement
- Derived: True
- Derived Req Justification: Staged power up is required for proper startup of the processor and it's periphals.
- Safety: False

##### 2047
The first stage in the power on sequence shall enable the TPS65400 Quad Switcher which sources the P1V0, P1V8 and P1V2 rails.
- Category: Requirement
- Derived: True
- Derived Req Justification: These are the primary power rails.
- Safety: False

##### 2048
The P2V5 rail PSU shall be enabled after the P1V35 rail is enabled using the P2V5_EN (P1V35_BVR_RDY) external signal.
- Category: Requirement
- Derived: True
- Derived Req Justification: Allows for the 2.5V PSU to initialize before enabling.
- Safety: False

##### 2049
The VCORE rail PSU shall be enabled as soon as the QUADSW_PGOOD is asserted, indicating P1V8, P1V0 and P1V2 rails have come into spec.
- Category: Requirement
- Derived: True
- Derived Req Justification: Provides power to the processor when available.
- Safety: False

##### 2050
The P1V0, P1V8 and P1V2 PSU shall be enabled as soon as the P3V3_BP and P5V rails come into spec, as indicated by the signal BP_RAILS_OK going high.
- Category: Requirement
- Derived: True
- Derived Req Justification: Provides power to peripherals like the Ethernet PHY.
- Safety: False

##### 2051
VTT shall be enabled when SEQ_PGOOD is asserted.
- Category: Requirement
- Derived: True
- Derived Req Justification: Provides power to the processor and peripherals when as soon as available.
- Safety: False

##### 2052
This concludes the normal power up sequence.
- Category: Information

##### 2053
The power sequencing system shall begin the power down sequence when any of the backplane inputs go out of spec, (except during power up as described in SBC314C-HRS-2045)
- Category: Requirement
- Derived: True
- Derived Req Justification: SBC314C should power down when input power is below the required levels to maintain proper operation.
- Safety: False

##### 2054
The power sequencing system shall deassert BP_RAILS_OK when the power down sequence begins.
- Category: Requirement
- Derived: True
- Derived Req Justification: Let's the system know the primariy power rails are no longer going to be in spec.
- Safety: False

##### 2055
The power down sequence shall disable all the on-board power supply units and the in-line FET switches.
- Category: Requirement
- Derived: True
- Derived Req Justification: PSUs and FETs should be shut down during power down sequence.
- Safety: False

##### 2056
The power sequencing system shall attempt to restart when:
1) all monitored power supply rails (not including backplane inputs) are below their undervoltage thresholds, AND
2) at least 70ms has elapsed since BP_RAILS_OK was negated
Note: This requirement does not apply to the first power up. This requirement is waived for corner cases where it cannot be implemented in volatile logic, e.g. complete loss of all power for very brief periods.
- Category: Requirement
- Derived: True
- Derived Req Justification: The SBC314C should safely power up when power is available.
- Safety: False

##### 2057
The external signal PWRMGR_PGOOD_L shall be asserted whenever all the monitored power rails are in spec.
- Category: Requirement
- Derived: True
- Derived Req Justification: This signal turns on the GPIO bus switch and green board LED when power rails are in spec.
- Safety: False

#### 785: Voltage Monitoring
- Category: Heading

##### 786
The power manager shall enable software to monitor the voltages of all input power rails that are used by the board, with the exception of VBAT.
- Category: Requirement
- Derived: True
- Derived Req Justification: Software needs access to power monitors. VBAT excluded from monitoring to prevent premature drain of battery from sampling current.
- Safety: False
- Verification Method: Analysis, Design Proving Test

##### 788
The voltage monitor shall enable software to monitor all major power rails that are generated within the board.
[This requirement does not apply to linear regulators below 500mA capacity, or local rails that are derived from main rails using power switches]
- Category: Requirement
- Derived: False
- Safety: True
- Verification Method: Analysis

##### 1033
The SBC314C shall use a LTC2991IMS#PBF IC to monitor voltages per the table below:
- Category: Requirement
- Derived: True
- Derived Req Justification: Component decision to support power management. Implementation choices influenced by the voltage monitor IC used.
- Safety: False
- Verification Details: Inspection of schematic and BOM.
- Verification Method: Inspection

##### 1932
| LTC2991 Input #1 | Rail Monitored | Nominal Rail Voltage | Input Attenuation | Nominal Input Voltage |
| --- | --- | --- | --- | --- |
| V1 | P1V0 | +1.0V ± 3% | x 1 | +1.0V ± 3% |
| V2 | P1V2 | +1.2V ± 5% | x 1 | +1.2V ± 5% |
| V3 | P1V8 | +1.8V ± 5% | x 1 | +1.8V ± 5% |
| V4 | P2V5 | +2.5V ± 5% | x 1 | +2.5V ± 5% |
| V5 | P1V5_SSD | +1.5V ± 5% | x 1 | +1.5V ± 5% |
| V6 | VCC_VTT_DDR | +0.675V ± 1% | x 1 | +0.675V ± 1% |
| V7 | P3V3 | +3.3V ± 5% | x 1 | +3.3V ± 5% |
| V8 | P3V3_AUX | +3.3V ± 5% | x 1 | +3.3V ± 5% |
| LTC2991 Input #2 | Rail Monitored | Nominal Rail Voltage | Input Attenuation | Nominal Input Voltage |
| V1 | Not Used | - | - | - |
| V2 | Not Used | - | - | - |
| V3 | VCORE | 0.9875-1.025V ± 3% | x 1 | +1.006V ± 5% |
| V4 | P5V | +5V ± 5% | x 1/2 | +2.5V ± 5% |
| V5 | P1V35 | +1.35V ± 5% | x 1 | +1.35V ± 5% |
| V6 | P12V_AUX | +12V ± 5% | x 1/5.7 | +2.105V ± 5% |
| V7 | Not Used | - | - | - |
| V8 | Not Used | - | - | - |

###### 1933

###### 1934
LTC2991 Input #1

###### 1935
Rail Monitored

###### 1936
Nominal Rail Voltage

###### 1937
Input Attenuation

###### 2129
Nominal Input Voltage

###### 1938

###### 1939
V1

###### 1940
P1V0

###### 1941
+1.0V ± 3%

###### 1942
x 1

###### 2130
+1.0V ± 3%

###### 1943

###### 1944
V2

###### 1945
P1V2

###### 1946
+1.2V ± 5%

###### 1947
x 1

###### 2131
+1.2V ± 5%

###### 1948

###### 1949
V3

###### 1950
P1V8

###### 1951
+1.8V ± 5%

###### 1952
x 1

###### 2132
+1.8V ± 5%

###### 1953

###### 1954
V4

###### 1955
P2V5

###### 1956
+2.5V ± 5%

###### 1957
x 1

###### 2133
+2.5V ± 5%

###### 1958

###### 1959
V5

###### 1960
P1V5_SSD

###### 1961
+1.5V ± 5%

###### 1962
x 1

###### 2134
+1.5V ± 5%

###### 1963

###### 1964
V6

###### 1965
VCC_VTT_DDR

###### 1966
+0.675V ± 1%

###### 1967
x 1

###### 2135
+0.675V ± 1%

###### 1968

###### 1969
V7

###### 1970
P3V3

###### 1971
+3.3V ± 5%

###### 1972
x 1

###### 2136
+3.3V ± 5%

###### 1973

###### 1974
V8

###### 1975
P3V3_AUX

###### 1976
+3.3V ± 5%

###### 1977
x 1

###### 2137
+3.3V ± 5%

###### 1978

###### 1979
LTC2991 Input #2

###### 1980
Rail Monitored

###### 1981
Nominal Rail Voltage

###### 1982
Input Attenuation

###### 2138
Nominal Input Voltage

###### 1983

###### 1984
V1

###### 1985
Not Used

###### 1986
-

###### 1987
-

###### 2139
-

###### 1988

###### 1989
V2

###### 1990
Not Used

###### 1991
-

###### 1992
-

###### 2140
-

###### 1993

###### 1994
V3

###### 1995
VCORE

###### 1996
0.9875-1.025V ± 3%

###### 1997
x 1

###### 2141
+1.006V ± 5%

###### 1998

###### 1999
V4

###### 2000
P5V

###### 2001
+5V ± 5%

###### 2002
x 1/2

###### 2142
+2.5V ± 5%

###### 2003

###### 2004
V5

###### 2005
P1V35

###### 2006
+1.35V ± 5%

###### 2007
x 1

###### 2143
+1.35V ± 5%

###### 2008

###### 2009
V6

###### 2010
P12V_AUX

###### 2011
+12V ± 5%

###### 2012
x 1/5.7

###### 2144
+2.105V ± 5%

###### 2013

###### 2014
V7

###### 2015
Not Used

###### 2016
-

###### 2017
-

###### 2145
-

###### 2018

###### 2019
V8

###### 2020
Not Used

###### 2021
-

###### 2022
-

###### 2146
-

##### 1123
The allocation of power rails to the voltage monitor inputs is shown in the table.
The Full scale input voltage of the ADC in the LTC2991IMS#PBF is 3.3V.
- Category: Information

##### 789
The resolution of the voltage monitors shall be 1% of the nominal voltage, or better
- Category: Requirement
- Derived: True
- Derived Req Justification: Implementation decision to ensure monitor accuracy.
- Safety: False
- Verification Method: Analysis, Design Proving Test

##### 862
The board shall be reset whenever any of the monitored power rails are below specification.
- Category: Requirement
- Derived: True
- Derived Req Justification: Specification to protect stable functionality of the system, avoiding unknown states from inadequate power.
- Safety: False
- Verification Details: Board level test.
- Verification Method: Design Proving Test

##### 1830
The board shall remain in reset until all of the monitored power rails return to specification.
- Category: Requirement
- Derived: True
- Derived Req Justification: Specification to protect stable functionality of the system, avoiding unknown states from inadequate power.
- Safety: False
- Verification Details: Board level test.
- Verification Method: Design Proving Test

### 957: Clocking Scheme
- Category: Heading

#### 1035
The overall clocking scheme is shown in the figure below. [Not every clock is shown]
- Category: Information

#### 1826
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- Category: Information

#### 1036
Two completely independent clock trees are implemented.
- Category: Information

#### 1037: PCIe Express Clock Tree
- Category: Heading

##### 1038
The primary source of all the PCIe clocks shall be a Vectron VC801 oscillator. This is a 25MHz device, running at 1.8V supply voltage.
- Category: Requirement
- Derived: True
- Derived Req Justification: Vectron VC801 (formerly known as VCC4) oscillators are used because of their proven reliability on many Abaco wide temperature products.
- Safety: False
- Verification Details: Inspection of schematic and BOM.
- Verification Method: Inspection

##### 1040
The oscillator output shall feed into an IDT 9FGV0841 clock synthesiser. This device generates 5 differential, PCIe Gen2 quality, differential PCIe REFCLKs at 100MHz for the 5 PCIe endpoints on the SBC314C. [See the figure above for details]
- Category: Requirement
- Derived: True
- Derived Req Justification: This clock synthesizer conforms to the PCIe Base Specification Rev 3.0.
- Safety: False
- Verification Details: Inspection of schematic and BOM.
- Verification Method: Inspection

##### 1041
Spread-spectrum synthesis is supported by the synthesiser, but is not enabled on the SBC314C.
- Category: Information

#### 1043: Other Clocks
- Category: Heading

##### 1044
The other clocks on the SBC314C shall be generated using a second clock tree. The primary source here is a second Vectron VC801 running at 25MHz. This device runs at 3.3VAUX.
- Category: Requirement
- Derived: True
- Derived Req Justification: Various voltage level CMOS clocks and various frequencies are required to inferface with various board IC's.
- Safety: False
- Verification Details: Inspection of schematic
- Verification Method: Inspection

##### 1045
The second oscillator shall feed into an IDT 'Versaclock' 5P49V60 programmable synthesiser which generates the 100MHz SYSCLK.
- Category: Requirement
- Derived: True
- Derived Req Justification: The synthesiser used for non-PCIe clocks is the IDT ICS 5P49V60. This is very similar to the 5V49EE901 which is well proven on the SBC312, however the 5P49V60 provides multiple output voltage banks which is beneficial on the SBC314.
- Safety: False
- Verification Details: Inspection of schematic and BOM.
  Analysis of component datasheet.
- Verification Method: Inspection, Analysis

##### 1047
One DDRCLK, the memory reference clock for the CPU, at 1.8V. This will be set to 100MHz - which enables a DDR channel speeds of 1600MHz.
- Category: Information

##### 1048
One USB reference clock for the CPU, at 1.8V. This is set to the standard frequency of 24MHz.
- Category: Information

##### 1050
A 25MHz reference clock, at 2.5V connects to a 1:4 fanout buffer, type IDT ICS553S, that is used to generate copies of the 25MHz clock at 1.8V. These are used by the two Ethernet PHYs, the PCIe SATA bridge, and by the FPGA.
- Category: Information

##### 1051
The Versaclock is a non-volatile programmable device, which is programmed over I2C in the factory. This is managed within a special FPGA build which is used during factory programming and is not delivered to the end user.
- Category: Information

##### 1090
Without the special Versaclock clock programming FPGA code, the Versaclock is isolated from the other I2C busses. Failure to detect this device in an I2C bus scan is therefore NOT a board fault.
- Category: Information

### 507: Other Features
- Category: Heading

#### 1173: Watchdog
- Category: Heading

##### 509
The SBC314C shall incorporate a software enabled watchdog.
- Category: Requirement
- Derived: True
- Derived Req Justification: There are a number of special features included in an enhanced 'aviation-grade' watchdog.
- Safety: False
- Verification Details: Inspection of schematic and BOM.
- Verification Method: Inspection

##### 744
The watchdog timer circuit shall be in the disabled state after any processor reset.
- Category: Requirement
- Derived: True
- Derived Req Justification: There are a number of special features included in an enhanced 'aviation-grade' watchdog.
- Safety: False
- Verification Details: Inspection of schematic and BOM.
  Analysis of component datasheets.
- Verification Method: Inspection, Analysis

##### 1833
The watchdog timer shall have kick intervals (watchdog window) as follows:
Minimum: 180.0 ms
Typical: 220.9 ms
Maximum: 261.7 ms
- Category: Requirement
- Derived: True
- Derived Req Justification: Using the equations from TPS3850H01QDRCRQ1 datasheet, 3.3nF 1% cap will produce the shown intervals when the window watchdog lower boundary SET0 and SET1 bits = 1.
- Safety: False
- Verification Method: Analysis, Design Proving Test

##### 1174
The watchdog, when configured to do so, shall reset the processor and all other SBC components if a Minimum Kick violation (software Kick received before Minimum Kick Interval) occurs
- Category: Requirement
- Derived: True
- Derived Req Justification: There are a number of special features included in an enhanced 'aviation-grade' watchdog.
- Safety: False
- Verification Details: Board level test.
- Verification Method: Design Proving Test

##### 849
The watchdog, when configured to do so, shall assert the backplane SYSRESET output if a Minimum Kick violation (software Kick received before Minimum Kick Interval) occurs
- Category: Requirement
- Derived: True
- Derived Req Justification: There are a number of special features included in an enhanced 'aviation-grade' watchdog.
- Safety: False
- Verification Details: Board level test.
- Verification Method: Design Proving Test

##### 844
The watchdog, when configured to do so, shall reset the processor and all other SBC components if no software Kick is received within the Maximum Kick Interval
- Category: Requirement
- Derived: True
- Derived Req Justification: There are a number of special features included in an enhanced 'aviation-grade' watchdog.
- Safety: False
- Verification Details: Board level test.
- Verification Method: Design Proving Test

##### 845
The watchdog, when configured to do so, shall assert the backplane SYSRESET output if no software Kick is received within the Maximum Kick Interval
- Category: Requirement
- Derived: True
- Derived Req Justification: There are a number of special features included in an enhanced 'aviation-grade' watchdog.
- Safety: False
- Verification Details: Board level test.
- Verification Method: Design Proving Test

##### 748
Once configured by software, the watchdog trip logic shall be completely independent of the SBC processor function - including the processor clock, clock crystal, and any distribution/divide-down circuitry.
- Category: Requirement
- Derived: True
- Derived Req Justification: There are a number of special features included in an enhanced 'aviation-grade' watchdog.
- Safety: False
- Verification Details: Inspection of schematic and BOM.
  Analysis of component datasheets.
- Verification Method: Inspection, Analysis

##### 749
It shall be possible for software to determine that a reset occurred due to a watchdog expiry event
- Category: Requirement
- Derived: True
- Derived Req Justification: There are a number of special features included in an enhanced 'aviation-grade' watchdog.
- Safety: False
- Verification Details: Board level test.
- Verification Method: Design Proving Test

#### 940: I2C Bus slave Devices
- Category: Heading

##### 1064
Unless otherwise stated, all I2C addresses in this document use the 7-bit numbering convention
- Category: Information

##### 1055: I2C Bus Topology
- Category: Heading

###### 1056
There is one major I2C bus on the SBC314C:
1) The 'Main' bus. This is internal to the board and gives access from the CPU to various slave devices.
- Category: Information

###### 1060
A small number of extra devices are connected to a second CPU I2C bus (labelled 'Bus 3' below).
- Category: Information

###### 1175
There is also a factory bus that links the FPGA to the system clock synthesiser when a special factory load of FPGA program is loaded into the FPGA, otherwise the factory bus is not implemented in deployed FPGA code.
- Category: Information

###### 1508
There SHALL be an I2C bus connection to the VPX backplane SM bus.
- Category: Requirement
- Derived: False
- Safety: False
- Verification Details: Inspection of schematic and BOM.
  Analysis of component datasheets.
- Verification Method: Inspection, Analysis

###### 1061
The I2C bus topology is shown in the figure below:
- Category: Information

###### 2160
I2C Bus Topology
- Category: Information
- Picture: true
- PictureName: Picture2
- PictureNum: 2

##### 1065: Main I2C Bus
- Category: Heading

###### 1066
The slave addresses of devices connected to the Main I2C bus shall be:
- Category: Requirement
- Derived: True
- Derived Req Justification: These are actual addresses assigned to the elapsed time indicator and real time clock, per the data sheet.
- Safety: False
- Verification Method: Inspection

###### 2023
| Device | Address (Main Bus) - 7 bit | Full Details in |
| --- | --- | --- |
| Real Time Clock | 0x68 | below |
| Elapsed Time Indicator | 0x6B | below |
| Tempature Sensor | 0x4C | below |
| Voltage Monitor | 0x48 | below |
| Voltage Monitor | 0x49 | below |
| XMC Site | Variable |  |
| Voltage Regulator 1 | 0x58 | below |
| Voltage Regulator 2 | 0x69 | below |
| Test Access Card | Master |  |

###### 2030

###### 2031
Device

###### 2032
Address (Main Bus) - 7 bit

###### 2033
Full Details in

###### 2024

###### 2025
Real Time Clock

###### 2026
0x68

###### 2034
below

###### 2027

###### 2028
Elapsed Time Indicator

###### 2029
0x6B

###### 2035
below

###### 2071

###### 2072
Tempature Sensor

###### 2073
0x4C

###### 2074
below

###### 2067

###### 2068
Voltage Monitor

###### 2069
0x48

###### 2070
below

###### 2098

###### 2099
Voltage Monitor

###### 2100
0x49

###### 2101
below

###### 2063

###### 2064
XMC Site

###### 2065
Variable

###### 2066

###### 2059

###### 2060
Voltage Regulator 1

###### 2061
0x58

###### 2062
below

###### 2091

###### 2092
Voltage Regulator 2

###### 2093
0x69

###### 2094
below

###### 2087

###### 2088
Test Access Card

###### 2089
Master

###### 2090

###### 517: Elapsed Time Indicator (ETI)
- Category: Heading

###### 518
The SBC314C shall incorporate an Elasped Time Indicator
- Category: Requirement
- Derived: True
- Derived Req Justification: An elapsed time indicator is part of the standard requirements. The ETI chosen also includes a power cycle counter. This is present on earlier SBC designs and is a standard, although unwritten, expectation.
- Safety: False
- Verification Details: Inspection of schematic and BOM.
- Verification Method: Inspection

###### 706
The Elapsed Time Indicator shall also record a count of power cycles
- Category: Requirement
- Derived: True
- Derived Req Justification: An elapsed time indicator is part of the standard requirements. The ETI chosen also includes a power cycle counter. This is present on earlier SBC designs and is a standard, although unwritten, expectation.
- Safety: False
- Verification Details: Inspection of schematic and BOM.
  Analysis of component datasheet.
  Board level test.
- Verification Method: Inspection, Analysis, Design Proving Test

###### 1069
The ETI device shall be the Maxim DS1682
- Category: Requirement
- Derived: True
- Derived Req Justification: An elapsed time indicator is part of the standard requirements. The ETI chosen also includes a power cycle counter. This is present on earlier SBC designs and is a standard, although unwritten, expectation.
- Safety: False
- Verification Details: Inspection of schematic and BOM.
- Verification Method: Inspection

###### 1076: Real Time Clock (RTC)
- Category: Heading

###### 1077
The SBC314C shall include a Maxim DS3231 real-time clock device.
- Category: Requirement
- Derived: True
- Derived Req Justification: DS3231 device has been used on other designs.
- Safety: False
- Verification Details: Inspection of schematic and BOM.
- Verification Method: Inspection

###### 1078
The RTC shall keep time when the system is powered down, using either the VPX VBAT or P3V3_AUX inputs.
- Category: Requirement
- Derived: False
- Safety: False
- Verification Details: Inspection of schematic.
  Analysis of component datasheet.
  Board level test.
- Verification Method: Inspection, Analysis, Design Proving Test

###### 512: Temperature Sensors
- Category: Heading

###### 513
The SBC314C shall incorporate a temperature sensor that monitors the temperature of the CPU die
- Category: Requirement
- Derived: True
- Derived Req Justification: Required function for the SBC314C in accordance with marketing requirements, and standard practice for the product line.
- Safety: False
- Verification Details: Inspection of schematic and BOM.
  Analysis of component datasheet.
  Board level test.
- Verification Method: Inspection, Analysis, Design Proving Test

###### 514
The SBC314C shall incorporate a temperature sensor that monitors the temperature of the PCB
- Category: Requirement
- Derived: True
- Derived Req Justification: Required function for the SBC314C in accordance with marketing requirements, and standard practice for the product line.
- Safety: False
- Verification Details: Inspection of schematic and BOM.
  Analysis of component datasheet.
  Board level test.
- Verification Method: Inspection, Analysis, Design Proving Test

###### 783
The PCB temperature sensor shall be located in the area of highest average PCB temperature
- Category: Requirement
- Derived: True
- Derived Req Justification: Good design practice.
- Safety: False
- Verification Method: Analysis

###### 780
The temperature sensors shall support the range -40degC to +150degC or greater
- Category: Requirement
- Derived: True
- Derived Req Justification: Sensor should envelope expected temperatures.
- Safety: False
- Verification Method: Inspection

###### 781
The accuracy of the PCB temperature sensor IC shall be +/-3 degrees C or better
- Category: Requirement
- Derived: True
- Derived Req Justification: Consistent with capabilities of OnSemi ADT7461.
- Safety: False
- Verification Method: Design Proving Test

###### 782
The temperature sensor reading shall be available to software
- Category: Requirement
- Derived: True
- Derived Req Justification: Design choice.
- Safety: False
- Verification Details: Board level test.
- Verification Method: Design Proving Test

###### 1062
The temperature sensor device shall be the OnSemi ADT7461. This provides both the CPU die and PCB temperatures.
Note: The ADT7461 monitors both the CPU die and PCB temperatures by receiving measurements from both sensors, one remote (internal to the T2081 CPU) and one internal to the ADT7461.
- Category: Requirement
- Derived: True
- Derived Req Justification: In line with previous products, e.g. the SBC312. The SBC314 used the OnSemi ADT7461 temperature sensor to measure both the PCB temperature and CPU die temperature. This is a well proven solution from previous products.
- Safety: False
- Verification Details: Inspection of schematic and BOM.
- Verification Method: Inspection

###### 2058
When the CPU die temperature is outside of the programmed range, the termperature sensor shall generate an interrupt.
- Category: Requirement
- Derived: True
- Derived Req Justification: Required to detail the implementation of the ADT7461 THERM outputs.
- Safety: False

###### 2095
When the PCB temperature is outside of the programmed range, the termperature sensor shall generate an interrupt.
- Category: Requirement
- Derived: True
- Derived Req Justification: Required to detail the implementation of the ADT7461 THERM outputs.
- Safety: False

###### 1279: Voltage Monitor

###### 1280
The SBC314C shall incorporate a voltage monitor sensor that monitors all internal voltages on the SBC314C.
- Category: Requirement
- Derived: False
- Safety: True
- Verification Method: Analysis

###### 1281
The accuracy of the internal voltage monitor sensor shall be 1% or better.
- Category: Requirement
- Derived: True
- Derived Req Justification: Ensures accuracy of voltage reporting.
- Safety: False
- Verification Details: Inspection of schematic and BOM.
  Analysis of component datasheet.
- Verification Method: Inspection, Analysis

###### 1282
The voltage monitoring device shall be the Analog Devices LTC2991IMS#PBF. This provides voltage monitoring of all voltages used by the SBC314C.
- Category: Requirement
- Derived: True
- Derived Req Justification: Appropriate device to cover voltage monitoring requirements.
- Safety: False
- Verification Details: Inspection of schematic and BOM.
- Verification Method: Inspection

###### 1286: Voltage Regulator 1
- Category: Heading

###### 1288
The SBC314C shall incorporate a voltage regulator for the T2081 core voltage and P1V35 used by the SBC314C that is programmable and supports voltage monitoring of these voltages.
- Category: Requirement
- Derived: True
- Derived Req Justification: Necessary to support T2081 power requirements.
- Safety: False
- Verification Details: Inspection of schematic and BOM.
  Analysis of component datasheet.
- Verification Method: Inspection, Analysis

###### 1289
The accuracy of the P1V35 reg voltage monitor shall be 1% or better.
- Category: Requirement
- Derived: True
- Derived Req Justification: Ensures accuracy of voltage monitoring.
- Safety: False
- Verification Details: Inspection of schematic and BOM.
  Analysis of component datasheet.
- Verification Method: Inspection, Analysis

###### 1291
The P1V35 voltage regulator device shall be the Texas Instruments TPS53681RSB. This provides programmable T2081 core voltage and P1V35 voltages and supports voltage monitoring of these voltages.
- Category: Requirement
- Derived: True
- Derived Req Justification: Appropriate device to cover voltage monitoring requirements.
- Safety: False
- Verification Details: Inspection of schematic and BOM.
- Verification Method: Inspection

###### 1287: Voltage Regulator 2
- Category: Heading

###### 1292
The SBC314C shall incorporate a voltage regulator for the P1V0, P1V8 and P1V2 voltages used by the SBC314C that is programmable and supports voltage monitoring of these voltages.
- Category: Requirement
- Derived: True
- Derived Req Justification: Necessary to support SBC314C power requirements.
- Safety: False
- Verification Details: Inspection of schematic and BOM.
  Analysis of component datasheet.
- Verification Method: Inspection, Analysis

###### 1293
The accuracy of the P1V0, P1V8, and P1V2 reg voltage monitor shall be 1% or better.
- Category: Requirement
- Derived: True
- Derived Req Justification: Ensures accuracy of voltage monitoring.
- Safety: False
- Verification Details: Inspection of schematic and BOM.
  Analysis of component datasheet.
- Verification Method: Inspection, Analysis

###### 1295
The P1V0, P1V8, P1V2 voltage regulator device shall be the Texas Instruments TPS65400RGZ. This provides programmable P1V0, P1V8 and P1V2 voltages used by the SBC314C and supports voltage monitoring of these voltages.
- Category: Requirement
- Derived: True
- Derived Req Justification: Appropriate device to cover voltage monitoring requirements.
- Safety: False
- Verification Details: Inspection of schematic and BOM.
- Verification Method: Inspection

##### 2102: CPU I2C Bus 2

###### 2103
There will be no I2C slave devices on CPU I2C Bus 2.
- Category: Information

##### 1079: CPU I2C Bus 3
- Category: Heading

###### 1080
The slave address of device connected to CPU I2C bus 3 is listed below:
Device Address (Sensor Bus) – 7 bit
t PCIe Switch 0x38 - see PCIe switch section and device data sheet for details
tails
- Category: Information

##### 1177: Factory Bus
- Category: Heading

###### 1178
The slave address of the device connected to factory bus is listed below
Device Address (Sensor Bus) – 7 bit
t PCIe Clock synthesiser 0x6A - see Clocking Scheme section for details
tails
- Category: Information

#### 519: Anti-Tamper (AT)
- Category: Heading

##### 520
The SBC314C shall connect any anti-tamper pin(s) provided by the CPU to the backplane
- Category: Requirement
- Derived: True
- Derived Req Justification: Necessary to read tamper status to external source.
- Safety: False
- Verification Details: Inspection of schematic and BOM.
  Analysis of component datasheet.
- Verification Method: Inspection, Analysis

#### 521: LEDs
- Category: Heading

##### 522: BIT Fail (Red)
- Category: Heading

###### 523
The SBC314C shall include a red LED for BIT failure reporting
- Category: Requirement
- Derived: True
- Derived Req Justification: Common industry practice for BIT feedback.
- Safety: False
- Verification Details: Inspection of schematic and BOM.
  Analysis of component datasheet.
  Board level test.
- Verification Method: Inspection, Analysis, Design Proving Test

###### 524
The BIT Fail LED shall be illuminated at power up, and thereafter be software controlled
- Category: Requirement
- Derived: True
- Derived Req Justification: Ensures LED is always in a known state, and ensures proper illumination prior to software control.
- Safety: False
- Verification Details: Board level test.
- Verification Method: Design Proving Test

###### 925
The BIT Fail LED shall maintain its state over a software-initiated CPU reset
- Category: Requirement
- Derived: True
- Derived Req Justification: The BIT status LEDs must also maintain their state over a self-reset, so that they show a true progress indication if subsequent phases of the boot-up sequence fail.
- Safety: False
- Verification Details: Board level test.
- Verification Method: Design Proving Test

###### 1094
The FPGA will set the BIT Fail LED to illuminate on power up, with software control thereafter. It is powered from the backplane P3V3_AUX rail so that it continues to function even when main power is not available.
- Category: Information

###### 1253
The SBC314C shall drive the BIT_FAIL_L VPX output pin with the inverse of the BIT_FAIL bit in the LED_CONTROL register.
- Category: Requirement
- Derived: False
- Safety: False
- Verification Method: Analysis

##### 525: User Programmable (Yellow)
- Category: Heading

###### 526
The SBC314C shall include 2 yellow LEDs that are software controlled
- Category: Requirement
- Derived: True
- Derived Req Justification: Necessary for status feedback.
- Safety: False
- Verification Details: Inspection of schematic and BOM.
  Analysis of component datasheet.
- Verification Method: Inspection, Analysis

###### 926
The User Programmable Yellow LEDs shall maintain their state over a software-initiated CPU reset
- Category: Requirement
- Derived: True
- Derived Req Justification: The BIT status LEDs must also maintain their state over a self-reset, so that they show a true progress indication if subsequent phases of the boot-up sequence fail.
- Safety: False
- Verification Details: Board level test.
- Verification Method: Design Proving Test

###### 1095
These yellow LEDs are intended for the use of BIT software
- Category: Information

##### 527: BIT Pass (Green)
- Category: Heading

###### 528
The SBC314C shall include a green LED for BIT Pass reporting
- Category: Requirement
- Derived: True
- Derived Req Justification: Common practice for board level BIT reporting.
- Safety: False
- Verification Method: Inspection, Design Proving Test

###### 529
The BIT Pass LED shall be switched off at power up, and thereafter be software controlled
- Category: Requirement
- Derived: True
- Derived Req Justification: Ensures LED is in a known state before SW control.
- Safety: False
- Verification Method: Analysis, Design Proving Test

###### 927
The BIT Pass LED shall maintain its state over a software-initiated CPU reset
- Category: Requirement
- Derived: True
- Derived Req Justification: The BIT status LEDs must also maintain their state over a self-reset, so that they show a true progress indication if subsequent phases of the boot-up sequence fail.
- Safety: False
- Verification Method: Analysis, Design Proving Test

##### 530: Power Good (Green)
- Category: Heading

###### 531
The SBC314C shall include a green LED that shall be lit when all power rails are good
- Category: Requirement
- Derived: True
- Derived Req Justification: BIT function to ensure voltages are correct and stable.
- Safety: False
- Verification Method: Analysis, Design Proving Test

###### 1093
The Power Good LED is driven by the FPGA, which uses the voltage monitors in the Power Manager to determine the power status
- Category: Information

##### 532: Reset (Red)
- Category: Heading

###### 533
The SBC314C shall include a red LED that shall be lit when the board is in reset
- Category: Requirement
- Derived: True
- Derived Req Justification: Visual feedback during reset condition.
- Safety: False
- Verification Method: Analysis, Design Proving Test

###### 1097
This LED is directly connected to the hardware reset signal which is used by ICs in the 3.3V power domain
- Category: Information

##### 534: User Programmable (Tri-colour)
- Category: Heading

###### 535
The SBC314C shall include 2 tri-colour user-programmable LEDs
- Category: Requirement
- Derived: True
- Derived Req Justification: Necessary for BIT feedback indication.
- Safety: False
- Verification Method: Inspection

###### 1096
Due to space constraints, only two tri-colour user LEDs are provided. Further, these LEDs are the same ones that are used to implement two of the BIT yellow LEDs. It is intended that application software will be able to take over these LEDs after BIT has completed booting and is finished with them.
- Category: Information

##### 1098: PCIe Link Status
- Category: Heading

###### 1099
There are 14 green LEDs which indicate the up/down link status of the PCIe links - on and off board. The LEDs are directly connected to the PCIe switch - see that section for details of how the lanes are allocated. Note that one LED is provided for each lane (not each link).

###### 1104
A red LED is provided to indicate that the PCIe switch is asserting a fatal error condition. See the PCIe switch data sheet for details of what this means.
- Category: Information

##### 1100: Ethernet Link Status
- Category: Heading

###### 1101
For each Ethernet port, 2 yellow link status LEDs are provided. One indicates when the link is up, and blinks with link activity. The second indicates that the link is in a 1000Mbps mode.

##### 1102: SATA SSD Activity
- Category: Heading

###### 1103
A yellow LED is provided to indicate activity of the on-board NAND SSD. This is directly connected to the SSD.

#### 536: JTAG
- Category: Heading

##### 819
The SBC314C shall provide access to the processor COP interface via JTAG. The physical interface is via a proprietary Test Access Card (TAC) which is outside the normal mechanical envelope
- Category: Requirement
- Derived: True
- Derived Req Justification: The TAC must provide a JTAG interface to the CPU in order to support software debuggers.
- Safety: False
- Verification Method: Inspection

##### 1107
The CPU uses a dedicated JTAG chain from the TAC
- Category: Information

##### 909
The SBC314C shall connect the backplane VPX JTAG interface (on P0) to the JTAG interfaces of the XMC site.
- Category: Requirement
- Derived: True
- Derived Req Justification: In order to support in-field reprogramming of PLDs on mezzanine cards without removing the boards from a deployed system, the VPX P0 JTAG interface will be presented to the mezzanine sites. This is a request from a lead customer that we have agreed to implement.
- Safety: False
- Verification Method: Inspection

##### 1105
The device order on the backplane VPX JTAG interface is:
Backplane -> XMC site -> Backplane
- Category: Information

##### 1106
The SBC314C provides a route-through circuit so that the backplane chain continues to work when one or other socket is not populated. If a socket IS populated, then the mezzanine MUST either implement JTAG or loop the chain through, otherwise the other socket will not be reachable in the chain.
- Category: Information

##### 1108
The SBC314C provides no terminations on the mezzanine chain, since no active circuits are connected
- Category: Information

##### 537
There are no other external or customer JTAG requirements for the SBC314C.
- Category: Information

#### 754: Testability (Built-in-Test)
- Category: Heading

##### 755
Each device connected to an internal data bus shall include a read/write mechanism sufficient for the device's connection to be verified at run-time
- Category: Requirement
- Derived: True
- Derived Req Justification: Required for system testability.
- Safety: False
- Verification Method: Inspection, Analysis, Design Proving Test

##### 756
With the exception of RAM devices, each device connected to an internal data bus shall include a device ID that can be read by software.
- Category: Requirement
- Derived: True
- Derived Req Justification: Required for system testability.
- Safety: False
- Verification Method: Analysis, Design Proving Test

### 550: I/O Connections and Pinout
- Category: Heading

#### 551
There are no requirements for Front panel I/O on the SBC314C
- Category: Information

#### 1247
All I/O on the SBC314C SHALL conform to the pinouts specified in ICD FORCE2C-0HG-9001.
- Category: Requirement
- Derived: False
- Safety: False
- Verification Details: Inspection of schematic.
- Verification Method: Inspection

#### 588
The SBC314C shall be compatible with the MOD3-PAY-2F2U-16.2.3-3 OpenVPX Payload Module Profile
- Category: Requirement
- Derived: True
- Derived Req Justification: Required by marketing requirements.
- Safety: False
- Verification Details: Inspection of schematic.
- Verification Method: Inspection

#### 589
The SBC314C shall be compatible with the MOD3-PAY-2F2T-16.2.5-3 OpenVPX Payload Module Profile
- Category: Requirement
- Derived: True
- Derived Req Justification: Required by marketing requirements.
- Safety: False
- Verification Details: Inspection of schematic.
- Verification Method: Inspection

#### 876
The SBC314C P1 connector shall be configured for PCIe in accordance with ANSI/VITA 46.4-2012
- Category: Requirement
- Derived: False
- Safety: False
- Verification Details: Inspection of schematic.
- Verification Method: Inspection

#### 1245
The SBC314 shall provide Geographical Addresses (5 bits plus odd parity) via the P0 VPX connector in accordance with VITA 46.0
- Category: Requirement
- Derived: False
- Safety: False
- Verification Details: Inspection of schematic.
- Verification Method: Inspection

#### 998
The SBC314C VPX pinout is described in the module "SBC314C Pinout"
- Category: Information

#### 999
The SBC314C I/O pinout is shown in this figure.
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- Category: Information

### 621: Interoperability
- Category: Heading

#### 622
SBC314C interoperability may be demonstrated by Test or Analysis
- Category: Information

#### 626
Where relevant, all interoperability requirements apply to both tracked backplane and cabled chassis OpenVPX systems
- Category: Information

#### 627
Where relevant, all interoperability requirements include PCIe Gen 2 operation
- Category: Information

#### 628
The SBC314C shall be interoperable with the RAR15XC-1084D mezzanine
- Category: Requirement
- Derived: False
- Safety: False
- Verification Details: Inspection of schematic and BOM.
  Board level interop testing.
- Verification Method: Inspection, Design Proving Test

#### 1201
The SBC314C shall be interoperable with all component CCAs of the FORCE2C Mission Computer system when installed in the FORCE2C LRU.
- Category: Requirement
- Derived: False
- Safety: False
- Verification Details: Inspection of schematic and BOM.
  LRU level interop testing.
- Verification Method: Inspection, Design Proving Test

### 1203: Built-In Test (BIT)
- Category: Heading

#### 1205
PBIT SHALL detect and report corruption of configuration memory at power up.
- Category: Requirement
- Derived: False
- Safety: True
- Verification Method: Analysis

#### 1206
PBIT SHALL detect and report corruption of programmable device configuration at power up.
- Category: Requirement
- Derived: False
- Safety: True
- Verification Method: Analysis

#### 1207
PBIT SHALL test the address and data lines for stuck signal faults at power up.
- Category: Requirement
- Derived: False
- Safety: True
- Verification Method: Analysis

#### 1208: Ethernet BIT (SBC314C & FORCE2C XCC924C)
- Category: Heading

##### 1209
The 1000BASE-T Ethernet bus transceiver hardware SHALL be capable of detecting and reporting the message bit errors.
- Category: Requirement
- Derived: False
- Safety: True
- Verification Method: Analysis

##### 1210
The 1000BASE-T Ethernet bus transceiver hardware SHALL be capable of detecting and reporting the loss of message.
- Category: Requirement
- Derived: False
- Safety: True
- Verification Method: Analysis

##### 1211
The 1000BASE-T Ethernet bus transceiver hardware SHALL be capable of detecting and reporting the loss of bus.
- Category: Requirement
- Derived: False
- Safety: True
- Verification Method: Analysis

##### 1212
The Ethernet data bus hardware SHALL implement error detection and correction capability.
- Category: Requirement
- Derived: False
- Safety: True
- Verification Method: Design Proving Test

##### 1213
The Ethernet data bus hardware SHALL support transient data fault correction using retry.
- Category: Requirement
- Derived: False
- Safety: True
- Verification Method: Analysis

## 578: Electrical
- Category: Heading

### 579: Power
- Category: Heading

#### 580
The SBC314C shall draw operating power only from the 5.0V and 3.3V power rails on the VPX backplane
- Category: Requirement
- Derived: True
- Derived Req Justification: The vast majority of deployed 3U VPX systems do not provide 12V (although this is allowed by the OpenVPX spec). The SBC314 must NOT use 12V input power.
  The SBC314 draws the majority of its power from the backplane 5V supply.
  In order to increase efficiency and save an extra on-board power supply, the SBC314 will also be designed to draw 3.3V power from the VPX backplane.
  It is therefore NOT compatible with 5V-only deployed chassis. This is not felt to be a significant restriction because most current systems do provide 3.3V main power.
- Safety: False
- Verification Details: Inspection of schematic
- Verification Method: Inspection

#### 581
The SBC314C shall use VPX P3V3_AUX supply for system management and power control functions
- Category: Requirement
- Derived: True
- Derived Req Justification: Marketing requirement.
- Safety: False
- Verification Details: Inspection of schematic
- Verification Method: Inspection

#### 710
The SBC314C shall consume no more than 1A from the P3V3_AUX supply
- Category: Requirement
- Derived: False
- Safety: False
- Verification Details: Board level testing.
- Verification Method: Design Proving Test

#### 582
The SBC314C shall connect the backplane +/-12V power rails (P12V_AUX and N12V_AUX) to the mezzanine site, but shall not use these rails in any other way.
- Category: Requirement
- Derived: True
- Derived Req Justification: Marketing requirement.
- Safety: False
- Verification Details: Inspection of schematic
- Verification Method: Inspection

#### 584
The SBC314C shall consume <=20uA from the external battery power input
- Category: Requirement
- Derived: True
- Derived Req Justification: Marketing requirement.
- Safety: False
- Verification Details: Board level testing.
- Verification Method: Design Proving Test

#### 585
There are no Live Insertion or Hot Swap requirements for the SBC314C
- Category: Information

#### 1115
The on-board power circuits shall comply with the requirements listed in the 'SBC314C On-board Power Supplies' module
- Category: Requirement
- Derived: True
- Derived Req Justification: Directs reader to the correct module.
- Safety: False
- Verification Details: Inspection of "SBC314C On-Board Power Supplies" module.
  Inspection of schematic and BOM.
  Board level testing.
- Verification Method: Inspection, Design Proving Test

#### 1186
Any power storage devices onboard the SBC314C SHALL be capacitive.
Note: The intent of this requirement is to prohibit onboard batteries.
- Category: Requirement
- Derived: False
- Safety: False
- Verification Method: Inspection

#### 1197
The output of each internal voltage source shall be monitored.
- Category: Requirement
- Derived: True
- Derived Req Justification: Required for implementing power up sequence.
- Safety: True
- Verification Method: Analysis

### 895: Start up Time
- Category: Heading

#### 896
When no mezzanine card is fitted, the SBC314C shall release the CPU from power-on reset within 50ms of stable power being present at the backplane.
- Category: Requirement
- Derived: False
- Safety: False
- Verification Details: Board level hardware tests.
- Verification Method: Design Proving Test

#### 897
When a mezzanine card is fitted, the SBC314C shall release the CPU from power-on reset within 150ms of stable power being present at the backplane, given that the mezzanine itself asserts that it is ready within 100ms.
- Category: Requirement
- Derived: False
- Safety: False
- Verification Details: Board level hardware tests.
- Verification Method: Design Proving Test

#### 1252
The SBC314C shall perform a 'Fast Boot' when it senses a logic 0 on GPIO_VPX5 back plane pin at startup.
- Category: Requirement
- Derived: False
- Safety: False
- Verification Details: Board level hardware test.
- Verification Method: Design Proving Test

### 610: Power Consumption
- Category: Heading

#### 611
The power consumption of the SBC314C shall be characterised across the full operating temperature range
- Category: Documentation Requirement
- Derived: True
- Derived Req Justification: Good design practice for robustness.
- Safety: False
- Verification Details: Board level hardware test.
- Verification Method: Design Proving Test

#### 711
The power consumption of the SBC314C T2081 shall not exceed 55W (all processor cores at maximum load, at maximum temperature, all interfaces active, no mezzanine fitted).
- Category: Operational requirement
- Derived: False
- Safety: False
- Verification Details: Board level hardware test.
- Verification Method: Design Proving Test

#### 887
The inrush current on the 3.3V rail shall not exceed 1.0A for 20ms per VITA 65.0 section 3.2.4.
For this requirement, no mezzanine is fitted and the 10-90% rise time of the input is greater than 1ms.
- Category: Requirement
- Derived: True
- Derived Req Justification: Required for compliance with VITA standards.
- Safety: False
- Verification Details: Board level hardware test.
- Verification Method: Design Proving Test

#### 888
The inrush current on the 5V rail shall not exceed 5.5A for 20ms per VITA 65.0 section 3.2.4.
For this requirement, no mezzanine is fitted and the 10-90% rise time of the input is greater than 1ms.
- Category: Requirement
- Derived: True
- Derived Req Justification: Required for compliance with VITA standards.
- Safety: False
- Verification Details: Board level hardware test.
- Verification Method: Design Proving Test

### 1155: Electrical Isolation
- Category: Heading

#### 1156
The electrical resistance between the heatsink and circuit ground shall be at least 10Mohm at 500V d.c.
- Category: Requirement
- Derived: False
- Safety: False
- Verification Details: Analysis of schematic and mechanical drawing.
  Test with insulation tester on hardware.
- Verification Method: Analysis, Design Proving Test

#### 2104
The SBC314C shall provide 1MΩ @ 100Vdc isolation from Ethernet signals to CGND, and 10MΩ @ 100Vdc isolation from all other front panel I/O signals to CGND.
- Category: Requirement
- Derived: False
- Safety: False

## 553: Mechanical
- Category: Heading

### 554: Connectors
- Category: Heading

#### 555
The SBC314C shall utilize the Tyco 'rugged' RT-2R VPX connectors
- Category: Mechanical Requirement
- Derived: True
- Derived Req Justification: The SBC314 will use the recently-introduced RT-2R 'rugged' VPX connectors. This does increase the cost somewhat, but the enhanced vibration and insertion life performance justify this.
- Safety: False
- Verification Details: Inspection of BOM.
- Verification Method: Inspection

#### 556
The SBC314C shall support the Tyco 'enhanced' VPX guide blocks for use with RT-2R
- Category: Mechanical Requirement
- Derived: True
- Derived Req Justification: The hardware will be designed to include the 'enhanced' VPX guide blocks that accompany the RT-2R VPX connectors. Default builds will use the standard guide blocks.
- Safety: False
- Verification Details: Inspection of BOM.
- Verification Method: Inspection

#### 557
The SBC314C default build shall use the standard Tyco VPX guide blocks
- Category: Mechanical Requirement
- Derived: True
- Derived Req Justification: For complianc with standards.
- Safety: False
- Verification Details: Inspection of BOM.
- Verification Method: Inspection

#### 718
The SBC314C shall use unkeyed VPX guide blocks
- Category: Mechanical Requirement
- Derived: True
- Derived Req Justification: COTS builds of the SBC314 will use standard, unkeyed, VPX guide blocks. This is because the SBC314 is a general purpose card that can be used in a wide variety of deployed systems.
- Safety: False
- Verification Details: Inspection of BOM.
- Verification Method: Inspection

#### 1185
All SBC314C signal and power connections to/from other boards SHALL traverse printed circuit card traces and connector pins only.
- Category: Requirement
- Derived: False
- Safety: False
- Verification Method: Inspection

#### 1831
Any onboard wiring on the SBC314C SHALL be in accordance with IPC-A-610 Class 3.
- Category: Requirement
- Derived: False
- Safety: False
- Verification Method: Inspection

### 558: Form Factor
- Category: Heading

#### 882
The SBC314C shall be a 3U VPX plug-in module as defined in ANSI/VITA 46.0-2007
- Category: Requirement
- Derived: False
- Safety: False
- Verification Details: Inspection of mechanical drawing.
  Analysis of ANSI/VITA 46.0-2007
- Verification Method: Inspection, Analysis

#### 1147
The SBC314C shall be available in a 0.8" pitch conduction-cooled form factor compatible with VITA46.0
- Category: Mechanical Requirement
- Derived: False
- Safety: False
- Verification Details: Inspection of mechanical drawing.
- Verification Method: Inspection

#### 889
Conduction-cooled variants shall incorporate ejector handles
- Category: Mechanical Requirement
- Derived: True
- Derived Req Justification: Adhering to IEEE 1101.2-1992, section 5.6.2
- Safety: False
- Verification Details: Inspection of BOM.
- Verification Method: Inspection

#### 890
Conduction-cooled variants shall incorporate wedgelocks
- Category: Mechanical Requirement
- Derived: True
- Derived Req Justification: Adhering to IEEE 1101.2-1992, section 5.6.3
- Safety: False
- Verification Details: Inspection of BOM.
- Verification Method: Inspection

#### 899
Conduction-cooled variants shall incorporate the tertiary mezzanine mounting holes (per ANSI/VITA 20 Permission 3.4)
- Category: Mechanical Requirement
- Derived: True
- Derived Req Justification: Adhering to VITA 20 Permission 3.4
- Safety: False
- Verification Details: Inspection of mechanical drawing.
  Analysis of ANSI/VITA 20 Permission 3.4.
- Verification Method: Inspection, Analysis

#### 900
The conduction-cooled metalwork shall be compatible with mezzanines that incorporate the secondary thermal interface, and also with mezzanines that do not.
This may be achieved by offering different heatsink variants.
- Category: Mechanical Requirement
- Derived: True
- Derived Req Justification: The SBC314 needs to support mezzanines that include the secondary thermal interface, and also those that do not. Different heatsink variants are necessary to achieve this.
- Safety: False
- Verification Details: Analysis of layout.
- Verification Method: Analysis

### 574: Weight
- Category: Heading

#### 575
The SBC314C shall weigh 1.5 lbs or less in all conduction-cooled build levels.
- Category: Mechanical Requirement
- Derived: False
- Safety: False
- Verification Details: Test by weighing a fully assembled SBC314C.
- Verification Method: Design Proving Test

### 576: Mezzanine Features
- Category: Heading

#### 577
The SBC314C shall not use components greater than 1.5mm tall in the mezzanine keep-out area
- Category: Mechanical Requirement
- Derived: True
- Derived Req Justification: Prevents interference with XMC mezzanine board components.
- Safety: False
- Verification Details: Inspection of mechanical drawings.
- Verification Method: Inspection

#### 885
The SBC314C conduction cooled variants shall be compatible with mezzanines designed as 'conduction cooled without faceplace I/O' as defined in ANSI/VITA 20
- Category: Mechanical Requirement
- Derived: True
- Derived Req Justification: Adhering to VITA 20
- Safety: False
- Verification Details: Inspection of mechanical drawings.
  Analysis of ANSI/VITA 20.
- Verification Method: Inspection, Analysis

#### 886
The SBC314C conduction cooled variants shall include the fixed centre rib as defined in ANSI/VITA 20
- Category: Mechanical Requirement
- Derived: True
- Derived Req Justification: Adhering to VITA 20
- Safety: False
- Verification Details: Inspection of mechanical drawings.
- Verification Method: Inspection

### 883: Internal Clearances
- Category: Heading

#### 884
The SBC314C's internal clearances shall not reduce to zero when exposed to any combination of static, thermal and dynamic conditions experienced during operation
- Category: Mechanical Requirement
- Derived: True
- Derived Req Justification: Prevents damage to conformal coating, components, and board due to harsh environmental, transport, or operational conditions.
- Safety: False
- Verification Details: Hardware test under L5 conditions.
- Verification Method: Design Proving Test

## 563: Cooling
- Category: Heading

### 1119
The achievable performance (CPU core frequency) for the SBC314C T2081 variant shall be characterised for -40⁰C to +71⁰C. No minimum core frequency is specified.
- Category: Documentation Requirement
- Derived: True
- Derived Req Justification: SBC314C needs to operate over the temperature range -40⁰C to +71⁰C so its operating characteristics must be characterized over that operating range.
- Safety: False
- Verification Details: Test under L5 conditions.
- Verification Method: Production Test

### 2152
The SBC314C shall support FORCE2C LRU conduction cooling from -40⁰C to +71⁰C.
- Category: Requirement
- Derived: True
- Derived Req Justification: The LRU has no internal fans, so the SBC314C board must be designed to support conduction cooling.
- Safety: False

## 714: Manufacturing and Construction
- Category: Heading

### 708: Conformal Coating
- Category: Heading

#### 599
The SBC314C shall be compatible with the Abaco Systems Towcester conformal coating processes
- Category: Manufacturing Requirement
- Derived: False
- Safety: False
- Verification Details: Inspection of component placement.
- Verification Method: Inspection

#### 707
The SBC314C shall be conformally coated as standard.
- Category: Manufacturing Requirement
- Derived: False
- Safety: False
- Verification Details: Inspection of assembly drawing.
- Verification Method: Inspection

### 709: Underfilling
- Category: Heading

#### 601
The SBC314C shall be compatible with the Abaco Systems Towcester underfill processes
- Category: Manufacturing Requirement
- Derived: True
- Derived Req Justification: Per Towcester manufacturing processes.
- Safety: False
- Verification Details: Inspection of component placement.
- Verification Method: Inspection

#### 602
The SBC314C default build shall not be underfilled
- Category: Manufacturing Requirement
- Derived: True
- Derived Req Justification: The board will be designed to support the Abaco-IP Towcester underfill process, however this will only be carried out to special order. The side-effects of the underfill process (thermal cycle life reduction, rework difficulties, etc.) generally do not outweigh the benefits.
  The lead avionics customer has commented that underfill is NOT desired and would not be necessary in their use cases.
- Safety: False
- Verification Details: Inspection of assembly drawing, PCB layout.
- Verification Method: Inspection

### 590: Workmanship
- Category: Heading

#### 592
The SBC314C shall be manufactured in accordance with the IPC-610 class 3 workmanship standard
- Category: Manufacturing Requirement
- Derived: False
- Safety: False
- Verification Details: Inspection of assembly drawing.
- Verification Method: Inspection

### 593: PCB Design
- Category: Heading

#### 594
The SBC314C shall be designed in accordance with IPC-600 class 3 PCB design rules
- Category: Manufacturing Requirement
- Derived: False
- Safety: False
- Verification Details: Inspection of PCB layout design rules report.
- Verification Method: Inspection

#### 595
The SBC314C shall be designed to use high Tg FR4
- Category: Manufacturing Requirement
- Derived: True
- Derived Req Justification: Standard design practice for temperature robustness.
- Safety: False
- Verification Details: Inspection of PCB PO.
- Verification Method: Inspection

### 596: Flammability
- Category: Heading

#### 597
The SBC314C PCB shall be UL-94 V0 rated for flammability
- Category: Manufacturing Requirement
- Derived: True
- Derived Req Justification: Robust flammability resistant standard.
- Safety: False
- Verification Details: Inspection of PCB PO.
- Verification Method: Inspection

### 715: RoHS Compliance
- Category: Heading

#### 716
The SBC314C assembly shall be RoHS compliant
- Category: Manufacturing Requirement
- Derived: False
- Safety: False
- Verification Details: Inspection of BOM.
  Analysis of component data sheets.
- Verification Method: Inspection

### 1181: Other Compliance
- Category: Heading

#### 1182
The SBC314C shall be compliant with the current WEEE directive.
- Category: Requirement
- Derived: False
- Safety: False
- Verification Details: Inspection of QA reports
- Verification Method: Inspection

#### 1183
The SBC314C shall be compliant with the current REACH directive.
- Category: Requirement
- Derived: False
- Safety: False
- Verification Details: Inspection of QA reports
- Verification Method: Inspection

## 586: Other Requirements
- Category: Heading

### 603: Reliability
- Category: Heading

#### 1195
The probability of single event effects causing an uncorrected Single Bit Upset shall be less than 10e-7 per flight hour.
- Category: Requirement
- Derived: False
- Safety: True
- Verification Method: Analysis

#### 2037
The SBC314C shall respond in a safe manner to the application of conditions outside the bounds specified in these requirements.
NOTE: The safety engineer will analyze the procedures and results of all robustness tests in order to verify this requirement.
- Category: Requirement
- Derived: False
- Safety: True

### 605: Rear Transition Module
- Category: Heading

#### 606
The SBC314C shall be compatible with the existing VPX3UX300A-1041 Rear Transition Module (RTM)
- Category: Compatibility Requirement
- Derived: True
- Derived Req Justification: Since the SBC314 is intended as a technical insertion replacement for the SBC312, the SBC314 must function with the SBC312 RTM.
- Safety: False
- Verification Details: Inspection of schematic and BOM of SBC314C and RTM.
  Test board level interop test with RTM.
- Verification Method: Inspection, Design Proving Test

### 1836: Unused Functions
- Category: Heading

#### 1837
All unused functions in the SBC314C shall be deactivated until needed.
Note: Deactivated means the function is not active, and does not require isolation.
- Category: Requirement
- Derived: False
- Safety: False
- Verification Details: Analysis of SBC314C board design and FORCE2C component board designs.
- Verification Method: Analysis
